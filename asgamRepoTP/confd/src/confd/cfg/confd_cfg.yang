module confd_cfg {
  namespace "http://tail-f.com/ns/confd_cfg/1.0";
  prefix confd_cfg;
  tailf:id "";
  tailf:export none;

  import ietf-yang-types {
    prefix yang;
  }
  import ietf-inet-types {
    prefix inet;
  }
  import tailf-common {
    prefix tailf;
  }
  import tailf-xsd-types {
    prefix xs;
  }

  organization "Tail-f Systems";

  description
    "This module defines the confd.conf file structure.";

  revision 2017-02-21 {
    description
      "Released as part of ConfD-6.4.

       Changed default for /confdConfig/webui/audit to 'false'.";
  }

  revision 2017-01-16 {
    description
      "Released as part of ConfD-6.3.1.

       Added /confdConfig/netconf/writeTimeout.";
  }

  revision 2016-11-03 {
    description
      "Released as part of ConfD-6.3.

       Added /confdConfig/ssh/algorithms/dhGroup/{minSize,maxSize}.";
  }

  revision 2013-09-05 {
    description
      "Released as part of ConfD-4.3.2.";
  }

  typedef candidateImplementationType {
    type enumeration {
      enum confd { value 664387550; }
      enum external { value 1055777754; }
    }
  }

  typedef whoHistoryDateTimeFormatType {
    type enumeration {
      enum long { value 105537656; }
      enum short { value 2029155337; }
    }
  }

  typedef multiPatternOperationType {
    type enumeration {
      enum any { value 383440309; }
      enum all { value 2031982792; }
    }
  }

  typedef confirmUncommitedOnExitType {
    type enumeration {
      enum prompt { value 1796253006; }
      enum discard { value 664427145; }
      enum commit { value 128787545; }
    }
  }

  typedef tableBehaviorType {
    type enumeration {
      enum dynamic { value 1339207079; }
      enum suppress { value 1746378947; }
      enum enforce { value 868039165; }
    }
  }

  typedef rollNumbering {
    type enumeration {
      enum fixed { value 1180146474; }
      enum rolling { value 492733776; }
    }
  }

  typedef completionMetaInfoType {
    type enumeration {
      enum false { value 1249155036; }
      enum alt1 { value 1173421906; }
      enum alt2 { value 780021010; }
    }
  }

  typedef pipeHelpModeType {
    type enumeration {
      enum always { value 1980885055; }
      enum auto { value 1146214388; }
      enum never { value 1258673503; }
    }
  }

  typedef candidateStorageType {
    type enumeration {
      enum disk { value 334675513; }
      enum ram { value 781613798; }
      enum auto { value 1146214388; }
    }
  }

  typedef editWrapModeType {
    type enumeration {
      enum wrap { value 1386835265; }
      enum newline { value 100405574; }
      enum vt100 { value 321017956; }
    }
  }

  typedef cliTimezoneType {
    type enumeration {
      enum utc { value 1427039597; }
      enum local { value 2129802687; }
    }
  }

  typedef journalCompactionType {
    type enumeration {
      enum automatic { value 1726921432; }
      enum manual { value 48828153; }
    }
  }

  typedef configurationReplicationType {
    type enumeration {
      enum async { value 1368962940; }
      enum sync { value 2047869128; }
    }
  }

  typedef operationalPersistentType {
    type enumeration {
      enum confspec { value 2093298699; }
      enum always { value 1980885055; }
      enum never { value 1258673503; }
    }
  }

  typedef operationalReplicationType {
    type enumeration {
      enum never { value 1258673503; }
      enum always { value 1980885055; }
      enum persistent { value 1783422916; }
    }
  }

  typedef operationalReplicationModeType {
    type enumeration {
      enum async { value 1368962940; }
      enum sync { value 2047869128; }
    }
  }

  typedef snmpVersionType {
    type enumeration {
      enum v1 { value 1223356638; }
      enum v2c { value 406691283; }
    }
  }

  typedef dscpType {
    type uint8 {
      range "0 .. 63";
    }
  }

  typedef limitType {
    type union {
      type uint32;
      type unboundedType;
    }
  }

  typedef unboundedType {
    type enumeration {
      enum unbounded { value 1813338730; }
    }
  }

  typedef infinityType {
    type enumeration {
      enum infinity { value 1378257424; }
    }
  }

  typedef timeoutType {
    type union {
      type xs:duration;
      type infinityType;
    }
  }

  typedef rpcErrorType {
    type enumeration {
      enum close { value 1912083739; }
      enum inline { value 1987224790; }
    }
  }

  typedef dbAccessType {
    type enumeration {
      enum read-write { value 1464236954; }
      enum writable-through-candidate { value 532826246; }
    }
  }

  typedef pubkeyAuthenticationType {
    type enumeration {
      enum none { value 432063804; }
      enum local { value 2129802687; }
      enum system { value 1534086422; }
    }
  }

  typedef expirationWarningType {
    type enumeration {
      enum ignore { value 1852995428; }
      enum display { value 2135153981; }
      enum prompt { value 1796253006; }
    }
  }

  typedef auditUserNameType {
    type enumeration {
      enum always { value 1980885055; }
      enum known { value 584303659; }
      enum never { value 1258673503; }
    }
  }

  typedef defaultHandlingModeType {
    type enumeration {
      enum explicit { value 920928367; }
      enum trim { value 250701330; }
      enum report-all { value 1824535838; }
    }
  }

  typedef syslogVersionType {
    type enumeration {
      enum bsd { value 1701318; }
      enum 1 { value 1535449617; }
    }
  }

  typedef cliAuditLogType {
    type enumeration {
      enum all { value 2031982792; }
      enum none { value 432063804; }
      enum denied { value 1293974345; }
      enum allowed { value 1631106802; }
    }
  }

  typedef cliActionMapType {
    type enumeration {
      enum both { value 1577301616; }
      enum config { value 2105663071; }
      enum oper { value 1313484953; }
    }
  }

  typedef cliModeNameStyleType {
    type enumeration {
      enum short { value 2029155337; }
      enum two { value 87009233; }
      enum full { value 476261018; }
    }
  }

  typedef quoteStyleType {
    type enumeration {
      enum quote { value 883581901; }
      enum backslash { value 1857839842; }
    }
  }

  typedef modeInfoInAAAType {
    type enumeration {
      enum true { value 1808796341; }
      enum false { value 1249155036; }
      enum path { value 1002915403; }
    }
  }

  typedef modeInfoInAuditType {
    type enumeration {
      enum true { value 1808796341; }
      enum false { value 1249155036; }
      enum path { value 1002915403; }
    }
  }

  typedef enableDisplayLevelType {
    type enumeration {
      enum true { value 1808796341; }
      enum false { value 1249155036; }
      enum pipe { value 612053909; }
    }
  }

  typedef cliStyle {
    type enumeration {
      enum j { value 641834109; }
      enum c { value 589337185; }
      enum i { value 1541010383; }
    }
  }

  typedef rollbackType {
    type enumeration {
      enum full { value 476261018; }
      enum delta { value 1928409309; }
    }
  }

  typedef syslogFacilityType {
    type union {
      type bsdFacilityType;
      type intFacilityType;
    }
  }

  typedef bsdFacilityType {
    type enumeration {
      enum daemon { value 137874048; }
      enum authpriv { value 2143429981; }
      enum local0 { value 1223389442; }
      enum local1 { value 659974174; }
      enum local2 { value 388815177; }
      enum local3 { value 133202671; }
      enum local4 { value 1369253367; }
      enum local5 { value 37794477; }
      enum local6 { value 918612352; }
      enum local7 { value 1098748970; }
    }
  }

  typedef intFacilityType {
    type uint32 {
      range "min .. 2147483647";
    }
  }

  typedef cliMax {
    type uint32 {
      range "5 .. 2147483647";
    }
  }

  typedef rollMax {
    type uint32 {
      range "0 .. 2147483647";
    }
  }

  typedef hex8ValueType {
    type xs:hexBinary {
      tailf:value-length 8;
    }
  }

  typedef charType {
    type string {
      length 1;
    }
  }

  typedef falseType {
    type enumeration {
      enum false { value 1249155036; }
    }
  }

  typedef aliasQuoteType {
    type union {
      type falseType;
      type charType;
    }
  }

  typedef hex16ValueType {
    type xs:hexBinary {
      tailf:value-length 16;
    }
  }

  typedef verifyType {
    type uint32 {
      range "1 .. 3";
    }
  }

  typedef pendingChangesActionType {
    type enumeration {
      enum continue { value 1852005625; }
      enum fail { value 1504483183; }
    }
  }

  typedef developerLogLevelType {
    type enumeration {
      enum error { value 126243105; }
      enum info { value 2062105651; }
      enum trace { value 1896625767; }
    }
  }

  typedef snmpLogLevelType {
    type enumeration {
      enum error { value 126243105; }
      enum info { value 2062105651; }
    }
  }

  typedef netconfTraceFormatType {
    type enumeration {
      enum pretty { value 560733322; }
      enum raw { value 764753385; }
    }
  }

  typedef subagentNameType {
    type xs:token {
      length "min .. 31";
    }
  }

  typedef SNMPAgentNameType {
    type xs:token {
      length "min .. 31";
    }
  }

  typedef SNMPContextNameType {
    type xs:token {
      length "min .. 31";
    }
  }

  typedef cryptHashAlgorithmType {
    type enumeration {
      enum md5 { value 721897608; }
      enum sha-256 { value 1426210322; }
      enum sha-512 { value 945188773; }
    }
  }

  typedef cryptHashRoundsType {
    type uint32 {
      range "1000 .. 999999999";
    }
  }

  typedef runtimeReconfigurationType {
    type enumeration {
      enum config-file { value 2073952695; }
      enum namespace { value 1847615892; }
    }
  }

  typedef idType {
    type union {
      type uint64 {
        range "1 .. max";
      }
      type fixedIdType;
    }
  }

  typedef fixedIdType {
    type enumeration {
      enum confd { value 664387550; }
      enum user { value 1529217067; }
      enum root { value 1945751049; }
    }
  }

  typedef maxFilesType {
    type int64 {
      range "2 .. max";
    }
  }

  typedef X-Frame-OptionsType {
    type enumeration {
      enum DENY { value 864815184; }
      enum SAMEORIGIN { value 1594198254; }
      enum ALLOW-FROM { value 2088887798; }
    }
  }

  typedef dhGroupSizeType {
    type uint32 {
        range "1024 .. 8192";
    }
  }

  container confdConfig {
    description "ConfD configuration.";
    tailf:callpoint confd_cfg {
      tailf:internal;
    }
    leaf runtimeReconfiguration {
      type runtimeReconfigurationType;
      default config-file;
      description
        "Controls whether ConfD should find run-time modifiable
         configuration parameters in the configuration file
         (config-file setting) or whether ConfD should them from a
         namespace with the data stored in CDB. See further the
         Advanced Topics chapter in the User Guide as well as the
         confdconf/dyncfg example in the example collection.";
    }
    container ignoreBindErrors {
      presence "";
      leaf enabled {
        type boolean;
        default false;
        description
          "By default (false) ConfD will refuse to start if
           any of its nortbound agents fails to bind their
           respective ports. When enabled, this parameter
           forces ConfD to ignore that fatal error situation
           and instead it just issues a warning and disables
           the failing agent. The agent may be enabled by
           dynamically configuring a free port via some other
           nortbound interface.";
      }
    }
    container confdIpcAddress {
      presence "";
      description
        "ConfD listens by default on 127.0.0.1:4565 for incoming TCP
         connections from ConfD client libraries, such as CDB, MAAPI,
         the CLI, the external database
         API, as well as commands from the confd script (such as 'confd
         --reload').

         The IP address and port can be changed. If they are changed
         all clients using MAAPI, CDB et.c. must be re-compiled to
         handle this. See the deployment user-guide on how to do this.

         Note that there are severe security implications involved if
         ConfD is instructed to bind(2) to anything but localhost. Read
         more about this in the ConfD IPC section in the Advanced
         Topics section of the User Guide. Use the IP 0.0.0.0 if you
         want ConfD to to listen(2) on all IPv4 addresses.";
      leaf ip {
        type inet:ip-address;
        default "127.0.0.1";
        description
          "The IP address which ConfD listens to for incoming
           connections from libconfd.";
      }
      leaf port {
        type inet:port-number;
        default 4565;
        description
          "The port number which ConfD listens to for incoming
           connections from libconfd.";
      }
    }
    leaf-list confdIpcExtraListenIp {
      type inet:ip-address;
      description
        "A list of additional IPs to which we wish to bind the ConfD
         IPC listener. This is useful if we don't want to use the
         wildcard 0.0.0.0 address in order to never expose the ConfD IPC
         to certain interfaces.";
    }
    container confdExternalIpc {
      presence "";
      description
        "ConfD can be set up to use a different protocol than TCP for
         the IPC connections, see the Advanced Topics chapter in the
         User Guide for the details.";
      leaf enabled {
        type boolean;
        default false;
        description "Enables the user-provided IPC mechanism.";
      }
      leaf address {
        type string;
        mandatory true;
        description
          "The address where ConfD should listen for incoming client
           connections using the user defined protocol.";
      }
    }
    leaf confdIpcListenBacklog {
      type int32;
      default 25;
      description
        "The maximum length to which the queue of pending connections
         for the IPC sockets may grow (see the OS manual page for
         listen(2)). If a very large number of applications connect to
         ConfD more or less simultaneously at startup, this value may
         need to be raised to avoid connection failures. Note that the
         OS may restrict the length to a lower value, e.g. on Linux it
         is silently truncated to the value in
         /proc/sys/net/core/somaxconn - i.e. this value may also need
         to be raised.";
    }
    container confdIpcAccessCheck {
      presence "";
      description
        "ConfD can be configured to restrict access for incoming
         connections to the IPC listener sockets. The access check
         requires that connecting clients prove possession of a
         shared secret.";
      leaf enabled {
        type boolean;
        default false;
        description
          "If set to 'true', access check for IPC connections is enabled.";
      }
      leaf filename {
        type string;
        mandatory true;
        description
          "filename is the full path to a file containing the shared
           secret for the IPC access check. The file should be protected
           via OS file permissions, such that it can only be read by
           the ConfD daemon and client processes that are allowed to
           connect to the IPC listener sockets.";
      }
    }
    leaf enableSharedMemorySchema {
      type boolean;
      default false;
      description
        "If set to true, then a C program will be started that loads
         the schema into shared memory (which then can be accessed
         by e.g Python).";
    }
    leaf sharedMemorySchemaExecutable {
      type string;
      description
        "The executable that setup the shared memory holding the schema.
         Note that if the default value is changed, it must be specified
         as an absolute path (i.e containing the root directory and all
         other subdirectories leading to the executable).";
    }
    container loadPath {
      presence "";
      leaf-list dir {
        type string;
        description
          "The loadPath element contains any number of dir
           elements. Each dir element points to a directory path on
           disk which is searched for compiled YANG files (.fxs
           files), and a compiled clispec
           file (.ccl file) during daemon startup.";
      }
    }
    leaf stateDir {
      type string;
      mandatory true;
      description
        "This is where ConfD writes persistent state data.  Currently
         the only state files are 'running.invalid' which exists only
         if the running database status is invalid, which it will be if
         one of the database implementation fails during the two-phase
         commit protocol, 'global.data' which is used to store some
         data that needs to be retained across reboots, and 'schema'
         which is the filename of the shared memory holding the schema.";
    }
    leaf commitRetryTimeout {
      type timeoutType;
      default PT0S;
      description
        "Commit timeout in the ConfD backplane. This timeout controls
         for how long the commit operation will attempt to complete
         the operation when some other entity is locking the
         database, e.g. some other commit is in progress or some
         managed object is locking the database.";
    }
    leaf maxValidationErrors {
      type limitType;
      default 1;
      description
        "Controls how many validation errors are collected and
         presented to the user at a time.";
    }
    container subagents {
      presence "";
      description
        "Present only if ConfD runs as a master agent.  Lists all
         registered subagents.";
      leaf enabled {
        type boolean;
        default false;
        description
          "Whether ConfD should act as a master agent. When set to
           'true' this ConfD instance is a master agent.";
      }
      list subagent {
        key name;
        description "Parameters for a single subagent.";
        leaf name {
          type subagentNameType;
          description
            "The name of the subagent. It is used as a unique
             identifier of the subagent.  The name is included in the
             subagent events (see confd_lib_events(3)) generated by ConfD.";
        }
        leaf enabled {
          type boolean;
          default true;
          description
            "Whether the subagent should be considered by ConfD. When
             set to 'false' the subagent is ignored.";
        }
        container tcp {
          presence "";
          description
            "Parameters to be used when the masteragent communicates
             with the subagent over plain text TCP. This is more
             efficient than SSH, but TCP is non-standard.";
          leaf ip {
            type inet:ip-address;
            mandatory true;
            description
              "The IP address where the subagent listens for NETCONF
               TCP connections.";
          }
          leaf port {
            type inet:port-number;
            default 2023;
            description
              "The port where the subagent listens for NETCONF TCP
               connections.";
          }
          container confdAuth {
            description
              "In order to use NETCONF over TCP, the
               subagent must understand the ConfD proprietary TCP
               header, described in the NETCONF chapter in the ConfD
               User Guide.";
            leaf user {
              type string;
              mandatory true;
              description
                "The user name to be used for authorization on the subagent.";
            }
            leaf group {
              type string;
              mandatory true;
              description
                "The group name to be used for authorization on the subagent.";
            }
          }
        }
        container ssh {
          presence "";
          description
            "Parameters to be used when the masteragent communicates
             with the subagent over SSH.";
          leaf ip {
            type inet:ip-address;
            mandatory true;
            description
              "The IP address where the subagent listens for NETCONF
               SSH connections.";
          }
          leaf port {
            type inet:port-number;
            default 2022;
            description
              "The port where the subagent listens for NETCONF SSH
               connections.";
          }
          leaf user {
            type string;
            mandatory true;
            description
              "The SSH user name used for authentication at the subagent.";
          }
          leaf password {
            type string;
            mandatory true;
            description "The SSH user's password.";
          }
        }
        container mount {
          description
            "This parameter defines where in the data hierarchy the
             subagent is registered.  It consists of a path which must
             exist in the data model of the mastet agent, and the name
             of the node which the subagent implements.";
          leaf path {
            type string;
            mandatory true;
            description
              "The path, in restricted XPath syntax, where the
               subagent's data is mounted. The XPath is restricted as
               an instance-identifier (see confd_types(3)). To mount on
               the top level, use '/'. Note that the XPath expression
               must not contain any namespace prefixes.

               If the subagent mounts more than one node, this object
               is a space separated list of paths.";
          }
          leaf-list node {
            type xs:QName;
            description
              "The namespace and name of the top-level node in that
               namespace, as a QName.

               This leaf-list must be of
               the same length as the 'path' leaf.";
          }
        }
        leaf disableSubtreeOptimization {
          type boolean;
          default false;
          description
            "Whenever possible, the master agent sends a single
             subtree filter request, instead of one request for each
             object.  If the subagent cannot handle these requests,
             for any reason, set this parameter to 'true'.";
        }
      }
    }
    container notifications {
      presence "";
      description "This section defines settings which affect notifications.";
      container eventStreams {
        description "Lists all available notification event streams.";
        list stream {
          key name;
          description "Parameters for a single notification event stream.";
          leaf name {
            type xs:token;
            description "The name attached to a specific event stream.";
          }
          leaf description {
            type string;
            mandatory true;
            description
              "A descriptive text attached to a specific event stream.";
          }
          leaf replaySupport {
            type boolean;
            mandatory true;
            description
              "Signals if replay support is available for a specific
               event stream.";
          }
          container builtinReplayStore {
            presence "";
            description
              "Parameters for the built in replay store for this event
               stream.

               If replay support is enabled ConfD automatically stores
               all notifications on disk ready to be replayed should a
               NETCONF manager ask for logged notifications. The replay
               store uses a set of wrapping log files on disk (of a
               certain number and size) to store the notifications.

               The max size of each wrap log file (see below) should
               not be too large. This to acheive fast replay of
               notifications in a certain time range. If possible use a
               larger number of wrap log files instead.

               If in doubt use the recommended settings (see below).";
            leaf enabled {
              type boolean;
              default false;
              description
                "enabled is either 'true' or 'false'. If 'false', the
                 applications must implement its own replay support.";
            }
            leaf dir {
              type string;
              mandatory true;
              description
                "The wrapping log files will be put in this disk
                 location.";
            }
            leaf maxSize {
              type tailf:size;
              mandatory true;
              description
                "The max size of each log wrap file. The recommended
                 setting is approximately S10MB.";
            }
            leaf maxFiles {
              type maxFilesType;
              mandatory true;
              description
                "The max number of log wrap files. The recommended
                 setting is around 50 files.";
            }
          }
        }
      }
    }
    container opcache {
      presence "";
      description
        "This section defines settings which affect the behavior of the
         operational data cache.";
      leaf enabled {
        type boolean;
        default false;
        description
          "enabled is either 'true' or 'false'. If 'true', the cache
           is enabled.";
      }
      leaf timeout {
        type uint64 {
          range "0 .. max";
        }
        mandatory true;
        description "The amount of time to keep data in the cache, in seconds.";
      }
    }
    container configCache {
      presence "";
      description
        "This section defines settings which affect the behavior of the
         undocumented config data cache.";
      leaf enabled {
        type boolean;
        default false;
        description
          "enabled is either 'true' or 'false'. If 'true', the cache
           is enabled.";
      }
    }
    container snmpgw {
      presence "";
      description
        "This section defines settings which affect the behavior of the
         SNMP gateway.";
      leaf enabled {
        type boolean;
        default false;
        description
          "enabled is either 'true' or 'false'. If 'true', the gateway
           is enabled.";
      }
      leaf trapPort {
        type inet:port-number;
        description "The port number to listen for traps on.";
      }
      list agent {
        key name;
        description "Parameters for a single agent.";
        leaf name {
          type SNMPAgentNameType;
          description "A name for the agent, mainly used for error reporting.";
        }
        leaf subscriptionId {
          type xs:token;
          description
            "The subscription id is used for indicating to which
             applications external traps should be sent.";
        }
        leaf forwardNotifStream {
          type xs:token;
          description
            "The forwarding notification stream , if present, indicates that
             traps should be automatically translated in accordance with the
             yang definition of the notification, and sent out on the
             given stream.
             The given stream may not implement replay support externally.";
        }
        leaf enabled {
          type boolean;
          default true;
          description
            "enabled is either 'true' or 'false'. If 'true', the agent
             is enabled.";
        }
        leaf community {
          type string;
          default private;
          description
            "The community string for communication with the agent. If
             the community string cannot be expressed in Unicode, use
             the element community_bin instead (see below). If both
             community_bin and community are specified, community is
             ignored.";
        }
        leaf community_bin {
          type xs:hexBinary;
          description
            "The community string for communication with the agent,
             encoded in hexBinary. For example,
             <community>AB</community> and
             <community_bin>4142</community_bin> are
             equivalent. The main use for this is when the community
             string cannot be expressed in Unicode.";
        }
        leaf version {
          type snmpVersionType;
          default v2c;
          description
            "The default protocol version to use. The value indicates
             the preferred version - if the agent doesn't respond, the
             other version will be tried.";
        }
        leaf timeout {
          type xs:duration;
          default PT5S;
          description
            "The amount of time to wait for an answer from the agent
             before aborting the operation. The default is five
             seconds.";
        }
        leaf ip {
          type inet:ip-address;
          mandatory true;
          description
            "The host (specified as a name or an IP address) on which
             the agent is running.";
        }
        leaf port {
          type inet:port-number;
          default 161;
          description
            "The port number to use for communication with the agent.";
        }
        leaf-list module {
          type string;
          description
            "A list of MIB module names that this agent implements.
             Each such MIB must be convert to YANG and compiled with
             the --snmpgw flag to confdc.";
        }
      }
    }
    list hideGroup {
      key name;
      description
        "Hide groups that can be unhidden must be listed here. There
         can be zero, one or many hideGroup entries in the
         configuraion.

         If a hide group does not have a hideGroup entry, then it
         cannot be unhidden using the CLI 'unhide' command. However, it
         is possible to add a hideGroup entry to the confd.conf file
         and then use confd --reload to make it available in the CLI.
         This may be useful to enable for example a diagnostics hide
         groups that you do not even want accessible using a password.";
      leaf name {
        type string;
        description
          "Name of hide group. This name should correspond to a hide
           group name in some data model.";
      }
      leaf password {
        type tailf:md5-digest-string;
        default "";
        description
          "A password can optionally be specified for a hide group. If
           no password or callback is given then the hide group can be
           unhidden without giving a password.

           If a password is specified then the hide group cannot be
           enabled unless the password is entered.

           To completely disable a hide group, ie make it impossible to
           unhide it, remove the entire hideGroup container for that
           hide group.";
      }
      leaf callback {
        type string;
        description
          "A callback can optionally be specified for a hide group. If
           no callback or password is given then the hide group can be
           unhidden without giving a password.

           If a callback is specified then the hide group cannot be
           enabled unless a password is entered and the callback
           successfully verifies the password. Using a callback it is
           possible to have short lived unhide passwords and per-user
           unhide passwords.

           The callback must be registered as a command() callback with
           confd_register_action_cbs(), see confd_lib_dp(3). The 'path'
           argument to the callback is always 'hidegroup', while
           argv[0] is the name of the hide group, argv[1] is the name
           of the user issuing the unhide command, and argv[2] is the
           given password. The callback should return CONFD_OK to allow
           the unhiding, otherwise CONFD_ERR.";
      }
    }
    container cdb {
      presence "";
      leaf enabled {
        type boolean;
        default false;
        description
          "enabled is either 'true' or 'false'. If 'false', CDB is
           disabled.";
      }
      leaf persistent {
        type boolean;
        default true;
        description
          "If persistent is set to false CDB will operate in RAM-only
           mode. This is mostly useful if the ConfD node is to be a
           slave in a HA cluster.";
      }
      leaf journalCompaction {
        type journalCompactionType;
        default automatic;
        description
          "Controls the way the CDB configuration store does its
           journal compaction. Never set to anything but the default
           'automatic' unless there is an external mechanism which
           controls the compaction using the
           cdb_initiate_journal_compaction() API call.";
      }
      leaf dbDir {
        type string;
        description
          "dbDir is the directory on disk which CDB use for its storage
           and any temporary files being used. It is also the directory
           where CDB searches for initialization files.";
      }
      container initPath {
        presence "";
        leaf-list dir {
          type string;
          description
            "The initPath can contain any number of dir
             elements. Each dir element points to a directory path
             which CDB will search for .xml files before looking in
             dbDir. The directories are searched in the order they
             are listed.";
        }
      }
      leaf clientTimeout {
        type timeoutType;
        default infinity;
        description
          "clientTimeout specifies how long CDB should wait for a
           response to e.g. a subscription notification before
           considering a client unresponsive. If a client fails to call
           cdb_sync_subscription_socket() within the timeout period,
           CDB will syslog this failure and then, considering the
           client dead, close the socket and proceed with the
           subscription notifications. If set to infinity, CDB will
           never timeout waiting for a response from a client.";
      }
      leaf replication {
        type configurationReplicationType;
        default sync;
        description
          "When CDB replication is enabled (which it is when
           high-availability mode is enabled, see /confdConfig/ha)
           the CDB configuration stores can be replicated either
           asynchronously or synchronously.  With asynchronous
           replication, a transaction updating the configuration is
           allowed to complete as soon as the updates have been sent
           to the connected slaves.  With the default synchronous
           replication, the transaction is suspended until the
           updates have been completely propagated to the slaves, and
           the subscribers on the slaves (if any) have acknowledged
           their subscription notifications (see confd_lib_cdb(3)).";
      }
      container subscriptionReplay {
        presence "";
        leaf enabled {
          type boolean;
          default false;
          description
            "If enabled it is possible to request a replay of the
             previous subscription notification to a new cdb";
        }
      }
      container operational {
        presence "";
        description
          "Operational data can either be implemented by external
           callbacks, or stored in CDB (or a combination of both). The
           operational datastore is used when data is to be stored in
           CDB.";
        leaf enabled {
          type boolean;
          default false;
          description "Whether to enable storage of operational data in CDB.";
        }
        leaf dbDir {
          type string;
          description
            "dbDir is the directory on disk which CDB operational
             uses for its storage and any temporary files being
             used. If left unset (default) the same directory as
             dbDir for CDB is used.";
        }
        leaf persistent {
          type operationalPersistentType;
          default confspec;
          description
            "By default the decision on how operational data in CDB is
             stored (persistent or volatile) is decided for each
             element in the YANG data model, via the tailf:persistent
             substatement to tailf:cdb-oper, see
             tailf_yang_extensions(5). It is possible to
             override this by using this setting in confd.conf. If
             'never', CDB will only keep the operational datastore in
             RAM. And if set to 'always' all CDB stored operational
             data will be persistently backed to a file.";
        }
        leaf replication {
          type operationalReplicationType;
          default persistent;
          description
            "When CDB replication is enabled (which it is when
             high-availability mode is enabled, see /confdConfig/ha)
             the CDB operational store can optionally be replicated
             too. When set to 'persistent', only persistent operational
             data is replicated. When set to 'never', CDB operational
             is never replicated. Using 'always' means that both
             persistent and non-persistent data is replicated. Note
             however that non-persistent data is only replicated to
             connected slaves at the time of writing. I.e. when a new
             slave connects to the master, only the persistent data is
             synchronized from the master, even if 'always' is used.";
        }
        leaf replicationMode {
          type operationalReplicationModeType;
          default async;
          description
            "When CDB replication is enabled (which it is when
             high-availability mode is enabled, see /confdConfig/ha)
             the replication of the CDB operational store (according to
             /confdConfig/cdb/operational/replication) can be done
             either asynchronously or synchronously.  With the default
             asynchronous replication, an API call writing operational
             data will return as soon as the updates have been sent to
             the connected slaves. With synchronous replication, the
             API call will block until the updates have been completely
             propagated to the slaves.";
        }
      }
    }
    container ha {
      presence "";
      leaf enabled {
        type boolean;
        default false;
        description "Enables the high-availability mode.";
      }
      leaf ip {
        type inet:ip-address;
        default "0.0.0.0";
        description
          "Defines which IP address ConfD should use for incoming
           requests from other HA nodes.";
      }
      leaf port {
        type inet:port-number;
        default 4569;
        description
          "Defines which port number confd should use for incoming
           requests from other HA nodes.";
      }
      container externalIpc {
        presence "";
        leaf enabled {
          type boolean;
          default false;
          description
            "Enables a user-provided IPC mechanism for the
             communication between HA nodes. See the Advanced Topics
             chapter in the User Guide for further details.";
        }
        leaf address {
          type string;
          mandatory true;
          description
            "The address ConfD should use for incoming requests from
             other HA nodes when the user-provided IPC mechanism is
             enabled.  See the Advanced Topics chapter in the User
             Guide for further details.";
        }
      }
      leaf tickTimeout {
        type xs:duration;
        default PT20S;
        description
          "Defines the timeout between keepalive ticks sent between HA
           nodes.  The special value 'PT0' means that no keepalive
           ticks will ever be sent.";
      }
    }
    container encryptedStrings {
      presence "";
      description
        "encryptedStrings defines keys used to encrypt strings adhering
         to the types tailf:des3-cbc-encrypted-string and
         tailf:aes-cfb-128-encrypted-string as defined in the
         tailf-common YANG module, see the confd_types(3) manual page.";
      container DES3CBC {
        presence "";
        description
          "In the DES3CBC case three 64 bits (8 bytes) keys and a
           random initial vector are used to encrypt the string.
           The initVector element is only used when upgrading from
           versions before ConfD-6.2, but it is kept for backward
           compatibility reasons.";
        leaf key1 {
          type hex8ValueType;
          mandatory true;
        }
        leaf key2 {
          type hex8ValueType;
          mandatory true;
        }
        leaf key3 {
          type hex8ValueType;
          mandatory true;
        }
        leaf initVector {
          type hex8ValueType;
        }
      }
      container AESCFB128 {
        presence "";
        description
          "In the AESCFB128 case one 128 bits (16 bytes) key and a
           random initial vector are used to encrypt the string.
           The initVector element is only used when upgrading from
           versions before ConfD-6.2, but it is kept for backward
           compatibility reasons.";
        leaf key {
          type hex16ValueType;
          mandatory true;
        }
        leaf initVector {
          type hex16ValueType;
        }
      }
    }
    container cryptHash {
      presence "";
      description
        "cryptHash specifies how cleartext values should be hashed for
         leafs of the types ianach:crypt-hash,
         tailf:sha-256-digest-string, and tailf:sha-512-digest-string -
         see the confd_types(3) manual page.";
      leaf algorithm {
        type cryptHashAlgorithmType;
        default md5;
        description
          "algorithm can be set to one of the values 'md5', 'sha-256',
           or 'sha-512', to choose the corresponding hash algorithm for
           hashing of cleartext values for the ianach:crypt-hash type.";
      }
      leaf rounds {
        type cryptHashRoundsType;
        default 5000;
        description
          "For the 'sha-256' and 'sha-512' algorithms for the
           ianach:crypt-hash type, and for the
           tailf:sha-256-digest-string and tailf:sha-512-digest-string
           types, 'rounds' specifies how many times the hashing loop
           should be executed. If a value other than the default 5000
           is specified, the hashed format will have 'rounds=N$', where
           N is the specified value, prepended to the salt. This parameter
           is ignored for the 'md5' algorithm for ianach:crypt-hash.";
      }
    }
    container logs {
      presence "";
      description
        "This section defines settings which affect the logging done by ConfD.";
      container syslogConfig {
        presence "";
        description
          "Shared settings for how to log to syslog. Logs (see below) can be
           configured to log to file and/or syslog.  If a log is configured to
           log to syslog, the settings under /confdConfig/logs/syslogConfig are
           used used.";
        leaf version {
          type syslogVersionType;
          default bsd;
          description
            "version is either 'bsd' (traditional syslog) or '1' (new
             IETF syslog format:
             draft-ietf-syslog-protocol-16.txt). '1' implies that
             /confdConfig/logs/syslogConfig/udp/enabled must be set to
             true.";
        }
        leaf facility {
          type syslogFacilityType;
          default daemon;
          description
            "facility is either 'daemon', 'authpriv',
             'local0', ..., 'local7' or an
             unsigned integer. This facility setting is the default
             facility. It's also possible to set individual facilities
             in the different logs below. Furthermore with the
             syslogServers container described below it is possible to
             set default facility on a per server basis. If facility is
             explictly set for a log type, that item is used.";
        }
        container udp {
          presence "";
          description
            "This is a container for UDP syslog. This container can
             only contain the configuration for a single UDP syslog
             server. If we need more than one syslog server we must
             use the /confdConfig/logs/syslogConfig/syslogServers
             container instead. If the udp container is used, the
             syslogServers container is ignored.";
          leaf enabled {
            type boolean;
            default false;
            description
              "enabled is either 'true' or 'false'. If 'false',
               messages will be sent to the local syslog daemon.";
          }
          leaf host {
            type inet:host;
            mandatory true;
            description
              "host is either a domain name or an IPv4/IPv6 network
               address. UDP syslog messages are sent to this host.";
          }
          leaf port {
            type inet:port-number;
            default 514;
            description
              "port is a valid port number to be used in combination
               with /confdConfig/logs/syslogConfig/udp/host.";
          }
        }
        container syslogServers {
          presence "";
          description
            "This is an alternative way of specifying UDP
             syslog servers.
             If we use the /confdCfg/logs/syslogConfig/udp container this
             container is ignored, alternatively, if we use this container
             the /confdCfg/logs/syslogConfig/udp container is ignored.";
          list server {
            key host;
            description
              "A set of syslog servers that get a copy
               of all syslog messages.";
            leaf host {
              type inet:host;
              description
                "host is either a domain name or an IPv4/IPv6 network
                 address. UDP syslog messages are sent to this host.";
            }
            leaf port {
              type inet:port-number;
              default 514;
              description
                "port is the UDP port number where this syslog
                 server is listening.";
            }
            leaf version {
              type syslogVersionType;
              default bsd;
              description
                "version is either 'bsd' (traditional syslog) or '1' (new
                 IETF syslog format:
                 draft-ietf-syslog-protocol-16.txt).";
            }
            leaf facility {
              type syslogFacilityType;
              default daemon;
              description
                "facility is either 'daemon', 'local0', ..., 'local7' or an
                 unsigned integer.";
            }
            leaf enabled {
              type boolean;
              default true;
              description
                "enabled is either 'true' or 'false'. If 'false',
                 this syslog server will not get any udp messages.";
            }
          }
        }
      }
      container confdLog {
        presence "";
        description
          "confdLog is ConfD's daemon log. Check this log for startup
           problems of the ConfD daemon itself. This log is not
           rotated, i.e. use logrotate(8).";
        leaf enabled {
          type boolean;
          default true;
          description
            "enabled is either 'true' or 'false'. If 'true', the
             log is enabled.";
        }
        container file {
          presence "";
          leaf enabled {
            type boolean;
            default false;
            description
              "enabled is either 'true' or 'false'. If 'true', file
               logging is enabled.";
          }
          leaf name {
            type string;
            mandatory true;
            description "name is the full path to the actual log file.";
          }
        }
        container syslog {
          presence "";
          leaf enabled {
            type boolean;
            default false;
            description
              "enabled is either 'true' or 'false'. If 'true', syslog
               messages are sent.";
          }
          leaf facility {
            type syslogFacilityType;
            description
              "facility is either 'daemon', 'authpriv',
               'local0', ..., 'local7' or an
               unsigned integer. This optional value overrides the
               /confdConfig/logs/syslogConfig/facility for this
               particular log.";
          }
        }
      }
      container developerLog {
        presence "";
        description
          "developerLog is a debug log for troubleshooting user-written
           C code. Enable and check this log for
           problems with validation code etc. This log is enabled by
           default. In all other regards it can be configured as
           confdLog. This log is not rotated, i.e. use logrotate(8).";
        leaf enabled {
          type boolean;
          default true;
          description
            "enabled is either 'true' or 'false'. If 'true', the
             log is enabled.";
        }
        container file {
          presence "";
          leaf enabled {
            type boolean;
            default false;
            description
              "enabled is either 'true' or 'false'. If 'true', file
               logging is enabled.";
          }
          leaf name {
            type string;
            mandatory true;
            description "name is the full path to the actual log file.";
          }
        }
        container syslog {
          presence "";
          leaf enabled {
            type boolean;
            default false;
            description
              "enabled is either 'true' or 'false'. If 'true', syslog
               messages are sent.";
          }
          leaf facility {
            type syslogFacilityType;
            description
              "facility is either 'daemon', 'authpriv',
               'local0', ..., 'local7' or an
               unsigned integer. This optional value overrides the
               /confdConfig/logs/syslogConfig/facility for this
               particular log.";
          }
        }
      }
      leaf developerLogLevel {
        type developerLogLevelType;
        default info;
        description
          "Controls which level of developer messages are printed in
           the developer log.";
      }
      container auditLog {
        presence "";
        description
          "auditLog is an audit log recording successful and failed
           logins to the ConfD backplane. This log is enabled by
           default. In all other regards it can be configured as
           /confdConfig/logs/confdLog. This log is not rotated,
           i.e. use logrotate(8).";
        leaf enabled {
          type boolean;
          default true;
          description
            "enabled is either 'true' or 'false'. If 'true', the
             log is enabled.";
        }
        container file {
          presence "";
          leaf enabled {
            type boolean;
            default false;
            description
              "enabled is either 'true' or 'false'. If 'true', file
               logging is enabled.";
          }
          leaf name {
            type string;
            mandatory true;
            description "name is the full path to the actual log file.";
          }
        }
        container syslog {
          presence "";
          leaf enabled {
            type boolean;
            default false;
            description
              "enabled is either 'true' or 'false'. If 'true', syslog
               messages are sent.";
          }
          leaf facility {
            type syslogFacilityType;
            description
              "facility is either 'daemon', 'authpriv',
               'local0', ..., 'local7' or an
               unsigned integer. This optional value overrides the
               /confdConfig/logs/syslogConfig/facility for this
               particular log.";
          }
        }
      }
      leaf auditLogCommit {
        type boolean;
        default false;
        description
          "Controls whether the audit log should include messages about
           the resulting configuration changes for each commit to the
           running data store.";
      }
      container netconfLog {
        presence "";
        description
          "netconfLog is a log for troubleshooting NETCONF operations,
           such as checking why e.g. a filter operation didn't return
           the data requested. This log is enabled by default. In all
           other regards it can be configured as
           /confdConfig/logs/confdLog. This log is not rotated,
           i.e. use logrotate(8).";
        leaf enabled {
          type boolean;
          default true;
          description
            "enabled is either 'true' or 'false'. If 'true', the
             log is enabled.";
        }
        container file {
          presence "";
          leaf enabled {
            type boolean;
            default false;
            description
              "enabled is either 'true' or 'false'. If 'true', file
               logging is enabled.";
          }
          leaf name {
            type string;
            mandatory true;
            description "name is the full path to the actual log file.";
          }
        }
        container syslog {
          presence "";
          leaf enabled {
            type boolean;
            default false;
            description
              "enabled is either 'true' or 'false'. If 'true', syslog
               messages are sent.";
          }
          leaf facility {
            type syslogFacilityType;
            description
              "facility is either 'daemon', 'authpriv',
               'local0', ..., 'local7' or an
               unsigned integer. This optional value overrides the
               /confdConfig/logs/syslogConfig/facility for this
               particular log.";
          }
        }
      }
      container snmpLog {
        presence "";
        description
          "snmpLog is a log for tracing SNMP requests and
           responses. This log is disbled by default. In all other
           regards it can be configured as
           /confdConfig/logs/confdLog. This log is not rotated,
           i.e. use logrotate(8).";
        leaf enabled {
          type boolean;
          default true;
          description
            "enabled is either 'true' or 'false'. If 'true', the
             log is enabled.";
        }
        container file {
          presence "";
          leaf enabled {
            type boolean;
            default false;
            description
              "enabled is either 'true' or 'false'. If 'true', file
               logging is enabled.";
          }
          leaf name {
            type string;
            mandatory true;
            description "name is the full path to the actual log file.";
          }
        }
        container syslog {
          presence "";
          leaf enabled {
            type boolean;
            default false;
            description
              "enabled is either 'true' or 'false'. If 'true', syslog
               messages are sent.";
          }
          leaf facility {
            type syslogFacilityType;
            description
              "facility is either 'daemon', 'authpriv',
               'local0', ..., 'local7' or an
               unsigned integer. This optional value overrides the
               /confdConfig/logs/syslogConfig/facility for this
               particular log.";
          }
        }
      }
      leaf snmpLogLevel {
        type snmpLogLevelType;
        default info;
        description
          "Controls which level of SNMP pdus are printed in the SNMP
           log. The value 'error' means that only PDUs with
           error-status not equal to 'noError' are printed.";
      }
      container webuiBrowserLog {
        presence "";
        description
          "webuiBrowserLog makes it possible to log Javascript
           errors/exceptions in a log file on the target device instead
           of just in the browser's error console. This log is not
           enabled by default and is not rotated, i.e. use
           logrotate(8).";
        leaf enabled {
          type boolean;
          default false;
          description
            "enabled is either 'true' or 'false'. If 'true', the
             browser log is used.";
        }
        leaf filename {
          type string;
          mandatory true;
          description
            "The path to the filename where browser log entries should
             be written";
        }
      }
      container webuiAccessLog {
        presence "";
        description
          "webuAccessLog is an access log for the embedded ConfD Web
           server. This file adheres to the Common Log Format, as
           defined by Apache and others. This log is not enabled by
           default and is not rotated, i.e. use logrotate(8).";
        leaf enabled {
          type boolean;
          default false;
          description
            "enabled is either 'true' or 'false'. If 'true', the access
             log is used.";
        }
        leaf trafficLog {
          type boolean;
          default false;
          description
            "Is either 'true' or 'false'. If 'true', all HTTP(S)
             traffic towards the embedded Web server is logged in a
             log file named 'traffic.trace'. Beware: Do not use this
             log in a production setting. This log is not enabled by
             default and is not rotated, i.e. use  logrotate(8).";
        }
        leaf dir {
          type string;
          mandatory true;
          description
            "The path to the directory whereas the access log should be
             written to.";
        }
      }
      container netconfTraceLog {
        presence "";
        description
          "netconfTraceLog is a log for understanding and
           troubleshooting NETCONF protocol interactions.  When this
           log is enabled, all NETCONF traffic to and from ConfD is
           stored to a file.  By default, all XML is pretty-printed.
           This will slow down the NETCONF server, so be careful
           when enabling this log.  This log is not rotated, i.e. use
           logrotate(8).";
        leaf enabled {
          type boolean;
          default false;
          description
            "enabled is either 'true' or 'false'. If 'true', all
             NETCONF traffic is logged.";
        }
        leaf filename {
          type string;
          mandatory true;
          description
            "The name of the file where the NETCONF traffic trace log is
             written.";
        }
        leaf format {
          type netconfTraceFormatType;
          default pretty;
          description
            "The value 'pretty' means that the XML data is
             pretty-printed.  The value 'raw' means that it is not.";
        }
      }
      container xpathTraceLog {
        presence "";
        description
          "xpathTraceLog is a log for understanding and
           troubleshooting XPath evaluations.  When this log is
           enabled, the execution of all XPath queries evaluated by
           ConfD is logged to a file.

           This will slow down ConfD, so be careful when enabling
           this log.  This log is not rotated, i.e. use logrotate(8).";
        leaf enabled {
          type boolean;
          default false;
          description
            "enabled is either 'true' or 'false'. If 'true', all
             XPath execution is logged.";
        }
        leaf filename {
          type string;
          mandatory true;
          description
            "The name of the file where the XPath trace log is
             written.";
        }
      }
      container errorLog {
        presence "";
        description
          "errorLog is an error log used for internal logging from the
           ConfD daemon. It is used for troubleshooting the ConfD
           daemon itself, and should normally be disabled. This log is
           rotated by the ConfD daemon (see below).";
        leaf enabled {
          type boolean;
          default false;
          description
            "enabled is either 'true' or 'false'. If 'true', error
             logging is performed.";
        }
        leaf filename {
          type string;
          mandatory true;
          description
            "filename is the full path to the actual log file. This
             parameter must be set if the errorLog is enabled.";
        }
        leaf maxSize {
          type tailf:size;
          default S1M;
          description
            "maxSize is the maximum size of an individual log file
             before it is rotated. Log filenames are reused when five
             logs have been exhausted.";
        }
        container debug {
          presence "";
          leaf enabled {
            type boolean;
            default false;
          }
          leaf level {
            type uint16;
            default 2;
          }
          leaf-list tag {
            type xs:token;
          }
        }
      }
    }
    container datastores {
      presence "";
      description
        "datastores defines which datastores the ConfD daemon should be
         setup to handle.";
      container startup {
        description
          "ConfD may keep separate running and startup configuration
           databases. When the system reboots for whatever reason, the running
           config database is lost, and the startup is read.";
        leaf enabled {
          type boolean;
          default false;
          description
            "enabled is either 'true' or 'false'. If 'true', a startup
             database is managed. Enable this only if our system uses a
             separate startup and running database.";
        }
      }
      container candidate {
        description
          "ConfD may keep a shared, named alternative configuration
           database which can be modified without impacting the running
           configuration. Changes in the candidate can be commit to
           running, or discarded.";
        leaf enabled {
          type boolean;
          default true;
          description
            "enabled is either 'true' or 'false'. If 'true', a
             candidate database is managed. Enable this if we want our
             users to use this feature from NETCONF, CLI or Webui, or
             other agents.";
        }
        leaf implementation {
          type candidateImplementationType;
          default confd;
          description
            "implementation is either 'confd' or 'external'. By
             default, ConfD implements the candidate configuration
             without impacting the application. But if our system
             already implements the candidate itself, set
             'implementation' to 'external'. This implies that the
             'external' candidate implementation must implement 5 C
             function callbacks for candidate manipulatation. (See
             confd_lib_dp(3) and the example 'misc/extern_candidate'.

             If subagents are used, 'implementation' must be set to
             'external'.";
        }
        leaf storage {
          type candidateStorageType;
          default auto;
          description
            "storage is either 'disk', 'ram', or 'auto'.
             disk
                ConfD always stores the candidate on
                disk. 'filename' must also be set (see below).
             ram
                ConfD always stores the candidate in
                ram. NOTE: If this alternative is
                used the implementation is not fully NETCONF
                compliant if confirmed-commit is enabled. The reason
                is that when confirmed-commit is used, the system
                must rollback to the previous configuration if it
                reboots but RAM data are lost.
             auto
                ConfD stores the candidate on disk if absolutely
                necessary for proper operation; otherwise it is
                stored in ram. 'filename' must also be set (see
                below).";
        }
        leaf filename {
          type string;
          description
            "filename is the name of the file where the candidate will
             be stored, if implementation is 'confd' and 'storage' is
             'disk' or 'auto'.";
        }
      }
      container running {
        presence "";
        description
          "By default, the running configuration is writable. This
           means that the application must be prepared to handle
           dynamic changes to the configuration.";
        leaf access {
          type dbAccessType;
          default read-write;
          description
            "access is either 'read-write' or
             'writable-through-candidate'. If
             'writable-through-candidate', the candidate datastore must
             be enabled.";
        }
      }
    }
    container scripts {
      presence "";
      description
        "It is possible to add scripts to control various things in
         ConfD, such as post-commit callbacks. New CLI commands can
         also be added. The scripts must be stored under
         /confdConfig/scripts/dir where there is a sub-directory for
         each script category. For some script categories it suffices
         to just add a script in the correct the sub-directory in
         order to enable the script. For others some configuration
         needs to be done.";
      leaf-list dir {
        type string;
        description
          "The directory path to the location of plug-and-play scripts. The
           scripts directory must have the following sub-directories:

              scripts/command/
                      policy/
                      post-commit/";
      }
    }
    leaf defaultHandlingMode {
      type defaultHandlingModeType;
      default explicit;
      description
        "defaultHandlingModeType is either 'explicit', 'trim', or
         'report-all'.  This parameter controls how default values
         for leafs are handled in the northbound interfaces.
         explicit
            If a value is set over a northbound interface, it is not
            considered default.

            Default values are not displayed in northbound
            interfaces, unless asked for by the user.
          trim
            If a value is set over a northbound interface, it is
            considered default if it is equal to the data model's
            default value.

            Values equal to the data model's default value are not
            displayed in northbound interfaces, unless asked for by
            the user.
          report-all
            All values are logically stored in the data store, and
            displayed in northbound interfaces.

         If the data store has the capability to handle default
         values, which for example CDB has, it will work with all
         values for this parameter.  In this case, default values are
         never actaully stored in the data store.  The value of this
         parameter should be choosen to give the end-user the best
         experience.

         If the data store does not have the capability to handle
         default values, this parameter should be set to
         'report-all'.";
    }
    leaf sortTransactions {
      type boolean;
      default true;
      description
        "This parameter controls how ConfD lists newly created, not yet
         committed dynamic elements.  If this value is set to 'false',
         ConfD will list all new elements before listing existing data.
         This was the only behavior in pre 2.5 versions of ConfD.

         If this value is set to 'true', ConfD will merge new and
         existing entries, and provide one sorted view of the data.
         This behavior works well when CDB is used to store
         configuration data, but if an external data provider is used,
         ConfD does not know the sort order, and can thus not merge the
         new entries correctly.  If an external data provider is used
         for configuration data, and the sort order differs from CDB's
         sort order, this parameter should be set to 'false'.";
    }
    leaf enableAttributes {
      type boolean;
      default false;
      description
        "This parameter controls if ConfD's attribute feature should
         be enabled or not.  Currently there are three attributes;
         'annotation', 'tags', and 'inactive'.  These are available
         in northbound interfaces (e.g. the annotate command in the
         CLI, and annotation XML attribute in NETCONF), but in order
         to be useful they need support from the underlying
         configuration data provider.  CDB supports attributes, but
         if an external data provider is used for configuration data,
         and it does not support the attribute callbacks, this
         parameter should be set to 'false'.";
    }
    leaf enableInactive {
      type boolean;
      default false;
      description
        "This parameter controls if the ConfD's inactive feature
         should be enabled or not.  This feature also requires
         enableAttributes to be enabled.";
    }
    container sessionLimits {
      presence "";
      description "Parameters for limiting concurrent access to ConfD.";
      leaf maxSessions {
        type limitType;
        default unbounded;
        description
          "Puts a limit to the total number of concurrent sessions to ConfD.";
      }
      list sessionLimit {
        key context;
        description
          "Parameters for limiting concurrent access for a specific
           context to ConfD. There can be multiple instances of this
           container element, each one specifying parameters for a
           specific context.";
        leaf context {
          type xs:token;
          description
            "The context is either one of cli, netconf, webui, snmp
             or it can be any other context string defined through
             the use of MAAPI. As an example, if we use MAAPI to
             implement a CORBA interface to ConfD, our MAAPI program
             could send the string 'corba' as context.";
        }
        leaf maxSessions {
          type limitType;
          mandatory true;
          description
            "Puts a limit to the total number of concurrent sessions to
             ConfD.";
        }
      }
      leaf maxConfigSessions {
        type limitType;
        default unbounded;
        description
          "Puts a limit to the total number of concurrent configuration
           sessions to ConfD.";
      }
      list configSessionLimit {
        key context;
        description
          "Parameters for limiting concurrent read-write transactions
           for a specific context to ConfD. There can be multiple
           instances of this container element, each one specifying
           parameters for a specific context.";
        leaf context {
          type xs:token;
          description
            "The context is either one of cli, netconf, webui, snmp,
             or it can be any other context string defined through
             the use of MAAPI. As an example, if we use MAAPI to
             implement a CORBA interface to ConfD, our MAAPI program
             could send the string 'corba' as context.";
        }
        leaf maxSessions {
          type limitType;
          mandatory true;
          description
            "Puts a limit to the total number of concurrent
             configuration sessions to ConfD for the corresponding
             context.";
        }
      }
    }
    container aaa {
      presence "";
      description
        "The login procedure to ConfD is fully described in the ConfD
         User Guide.";
      leaf sshServerKeyDir {
        type string;
        description
          "sshServerKeyDir is the directory file path where the keys
           used by the ConfD SSH daemon are found. This parameter must
           be set if SSH is enabled for NETCONF or the CLI. If SSH is
           enabled, the server keys used by ConfD are om the same
           format as the server keys used by openssh, i.e. the same
           format as generated by 'ssh-keygen'.

           Only DSA- and RSA-type keys can be used with the ConfD
           SSH daemon, as generated by 'ssh-keygen' with the '-t dsa'
           and '-t rsa' switches, respectively.

           The key must be stored with an empty passphrase, and
           with the name 'ssh_host_dsa_key' if it is a DSA-type key, and with
           the name 'ssh_host_rsa_key' if it is an RSA-type key.

           The SSH server will advertise support for those key
           types for which there is a key file available and for which
           the required algorithm is enabled, see the
           /confdConfig/ssh/algorithms/serverHostKey directive.";
      }
      leaf sshPubkeyAuthentication {
        type pubkeyAuthenticationType;
        default system;
        description
          "Controls how the ConfD SSH daemon locates the user keys for
           public key authentication.

           If set to 'none', public key authentication is disabled.

           If set to 'local', and the user exists in
           /aaa/authentication/users, the keys in the user's
           'ssh_keydir' directory are used.

           If set to 'system', the user is first looked up in
           /aaa/authentication/users, but only if
           /confdConfig/aaa/localAuthentication/enabled is set to
           'true' - if localAuthentication is disabled, or the user
           does not exist in /aaa/authentication/users, but the user
           does exist in the OS password database, the keys in the
           user's $HOME/.ssh directory are used.";
      }
      leaf sshLoginGraceTime {
        type xs:duration;
        default PT10M;
        description
          "ConfD closes ssh connections after this time if the client
           has not successfully authenticated itself by then. If the
           value is 0, there is no time limit for client authentication.

           This is a global value for all ssh servers in ConfD.

           Modification of this value will only affect ssh connections that
           are established after the modification has been done.";
      }
      leaf sshMaxAuthTries {
        type limitType;
        default unbounded;
        description
          "ConfD closes ssh connections when the client has made this
           number of unsuccessful authentication attempts.

           This is a global value for all ssh servers in ConfD.

           Modification of this value will only affect ssh connections that
           are established after the modification has been done.";
      }
      container aaaBridge {
        presence "";
        description
          "aaaBridge specifies if the aaa_bridge, as described in
           confd_aaa_bridge(1), will be used to access external AAA
           info.";
        leaf enabled {
          type boolean;
          default false;
          description
            "enabled is either 'true' or 'false'. If 'true', the
             confd_aaa_bridge program is automatically started by ConfD";
        }
        leaf file {
          type string;
          description
            "file specifies the location of the AAA data file needed by
             the confd_aaa_bridge program.";
        }
      }
      leaf defaultGroup {
        type string;
        description
          "If the group of a user cannot be found in the AAA
           sub-system, a logged in user will end up as a member of the
           default group (if specified).  If a user logs in and the
           group membership cannot be established, the user will have
           zero access rights.";
      }
      leaf authOrder {
        type string;
        description
          "By default the AAA system will try to authenticate a user in
           the following order. (1) localAuthentication i.e. the user
           is found inside /aaa/authentication/users. (2) pam - i.e PAM
           authentication - if enabled - is tried. (3) externalAuthentication
           i.e. an external program is invoked to authenticate the user.

           The default is thus:

           'localAuthentication pam externalAuthentication'

           To change the order - change this string. For example in
           order to always try pam authentication before local auth set
           it to: 'pam localAuthentication'";
      }
      leaf expirationWarning {
        type expirationWarningType;
        default ignore;
        description
          "When PAM or external authentication is used, the
           authentication mechanism may give a warning that the user's
           password is about to expire. This parameter controls how
           ConfD processes that warning message.

           If set to 'ignore', the warning is ignored.

           If set to 'display', interactive user interfaces will
           display the warning message at login time.

           If set to 'prompt', interactive user interfaces will
           display the warning message at login time, and require that
           the user acknowledges the message before proceeding.";
      }
      leaf auditUserName {
        type auditUserNameType;
        default always;
        description
          "Controls the logging of the user name when a failed
           authentication attempt is logged to the audit log.

           If set to 'always', the user name is always logged.

           If set to 'known', the user name is only logged when it is
           known to be valid (i.e. when attempting localAuthentication
           and the user exists in /aaa/authentication/users),
           otherwise it is logged as '[withheld]'.

           If set to 'never', the user name is always logged as
           '[withheld]'.";
      }
      container pam {
        presence "";
        description
          "If PAM is to be used for login the ConfD daemon typically
           must run as root.";
        leaf enabled {
          type boolean;
          default false;
          description "When set to 'true', ConfD uses PAM for authentication.";
        }
        leaf service {
          type string;
          default common-auth;
          description
            "The PAM service to be used for the authentication.
             This can be any service we have installed in
             the /etc/pam.d directory. Different unices have different
             services installed under /etc/pam.d - choose a service
             which makes sense or create a new one.";
        }
        leaf timeout {
          type xs:duration;
          default PT10S;
          description
            "The maximum time that authentication will wait for a reply
             from PAM. If the timeout is reached, the PAM
             authentication will fail, but authentication attempts may
             still be done with other mechanisms as configured for
             /confdConfig/aaa/authOrder. Default is PT10S, i.e. 10
             seconds.";
        }
      }
      container externalAuthentication {
        presence "";
        leaf enabled {
          type boolean;
          default false;
          description "When set to 'true', external authentication is used.";
        }
        leaf executable {
          type string;
          description
            "If we enable external authentication, an executable on the
             local host can be launched to authenticate a user.  The
             executable will receive the username and the cleartext
             password on its standard input. The format is
             '[${USER};${PASS};]\\n'. For example if user is 'bob' and
             password is 'secret', the executable will receive the string
             '[bob;secret;]' followed by a newline on its standard
             input. The program must parse this line.

             The task of the external program, which for example could
             be a RADIUS client, is to authenticate the user and also
             provide the user to groups mapping. Refer to the External
             authentication section of the AAA chapter in the User
             Guide for the details of how the program should report the
             result back to ConfD.";
        }
        leaf useBase64 {
          type boolean;
          default false;
          description
            "When set to true, ${USER} and ${PASS} in the data passed
             to the executable will be base64-encoded, allowing e.g. for
             the password to contain ';' characters. For example if user
             is 'bob' and password is 'secret', the executable will
             receive the string '[Ym9i;c2VjcmV0;]' followed by a newline.";
        }
        leaf includeExtra {
          type boolean;
          default false;
          description
            "When set to true, additional information items will be
             provided to the executable: source IP address and port,
             context, and protocol. I.e. the complete format will be
             '[${USER};${PASS};${IP};${PORT};${CONTEXT};${PROTO};]\\n'.
             Example: '[bob;secret;192.168.1.1;12345;cli;ssh;]\\n'.";
        }
      }
      container localAuthentication {
        presence "";
        leaf enabled {
          type boolean;
          default true;
          description
            "When set to true, ConfD uses local authentication. That
             means that the user data kept in the aaa namespace is used
             to authenticate users. When set to false some other
             authentication mechanism such as PAM or external
             authentication must be used.";
        }
      }
      container authenticationCallback {
        presence "";
        leaf enabled {
          type boolean;
          default false;
          description
            "When set to true, ConfD will invoke an application
             callback when authentication has succeeded or failed. The
             callback may reject an otherwise successful authentication.
             If the callback has not been registered, all
             authentication attempts will fail. See confd_lib_dp(3) for
             the callback details.";
        }
      }
      container authorization {
        presence "";
        leaf enabled {
          type boolean;
          default true;
          description
            "When set to false, all authorization checks are turned
             off, similar to the -noaaa flag in confd_cli.";
        }
        container callback {
          presence "";
          leaf enabled {
            type boolean;
            default false;
            description
              "When set to true, ConfD will invoke application
               callbacks for authorization. If the callbacks have not
               been registered, all authorization checks will be
               rejected. See confd_lib_dp(3) for the callback details.";
          }
        }
      }
      leaf namespace {
        type inet:uri;
        default "http://tail-f.com/ns/aaa/1.1";
        description
          "If we want to move the AAA data into another userdefine
           namespace, we indicate that here.";
      }
      leaf prefix {
        type string;
        default "/";
        description
          "If we want to move the AAA data into another userdefined
           namespace, we indicate the prefix path in that namespace
           where the ConfD AAA namespace has been mounted.";
      }
    }
    container rollback {
      presence "";
      description
        "Settings controlling if and where rollback files are
         created. A rollback file contains a copy of the system
         configuration. The current running configuration is always
         stored in rollback0, the previous version in rollback1
         etc. The oldest saved configuration has the highest suffix.";
      leaf enabled {
        type boolean;
        default false;
        description
          "When set to true a rollback file will be created whenever
           the running configuration is modified.";
      }
      leaf directory {
        type string;
        mandatory true;
        description "Location where rollback files will be created.";
      }
      leaf historySize {
        type uint32;
        default 35;
        description "Number of old configurations to save.";
      }
      leaf type {
        type rollbackType;
        default delta;
        description
          "Type of rollback file to use. If 'full' is specified, then a
           full configuration dump is stored in each rollback file.
           Rollback file 0 will always contain the running
           configuration.  If 'delta' is used, then only the changes
           are stored in the rollback file. Rollback file 0 will
           contain the changes from the last configuration.

           Using deltas is more space and time efficient for large
           configurations.  Full rollback files are more robust when
           multiple external databases are used. If the external
           databases becomes inconsistent a previous configuration can
           always be restored using a full rollback file.";
      }
      leaf rollbackNumbering {
        type rollNumbering;
        default rolling;
        description
          "rollbackNumbering is either 'fixed' or 'rolling'. If set
           to 'rolling' then rollback file '0' will always contain the
           last commit. When using 'fixed' each rollback will get
           a unique increasing number.";
      }
    }
    container ssh {
      presence "";
      description
        "This section defines settings which affect the behavior of the
         built in SSH implementation.";
      leaf idleConnectionTimeout {
        type xs:duration;
        default PT10M;
        description
          "The maximum time that an authenticated connection to the SSH
           server is allowed to exist without open channels. If the
           timeout is reached, the SSH server closes the connection.
           Default is PT10M, i.e. 10 minutes. If the value is 0, there
           is no timeout.";
      }
      container algorithms {
        presence "";
        description
          "This section defines custom lists of algorithms to be usable
           with the built-in SSH implementation.

           For each type of algorithm, an empty value means that all
           supported algorithms should be usable, and a non-empty value
           (a comma-separated list of algorithm names) means that the
           intersection of the supported algorithms and the configured
           algorithms should be usable.";
        leaf serverHostKey {
          type string;
          default "";
          description
            "The supported serverHostKey algorithms (if implemented in
             libcrypto) are 'ssh-dss' and 'ssh-rsa', but for any SSH server,
             it is limited to those algorithms for which there is a host key
             installed in the directory given by
             /confdConfig/aaa/sshServerKeyDir.

             To limit the usable serverHostKey algorithms to 'ssh-dss', set
             this value to 'ssh-dss' or avoid installing a key of any other
             type than ssh-dss in the sshServerKeyDir.";
        }
        leaf kex {
          type string;
          default "";
          description
            "The supported key exchange algorithms (as long as their hash
             functions are implemented in libcrypto) are
             'diffie-hellman-group-exchange-sha256',
             'diffie-hellman-group-exchange-sha1',
             'diffie-hellman-group14-sha1' and 'diffie-hellman-group1-sha1'.

             To limit the usable key exchange algorithms to
             'diffie-hellman-group14-sha1' and
             'diffie-hellman-group-exchange-sha256' (in that order) set this
             value to
             'diffie-hellman-group14-sha1,
             diffie-hellman-group-exchange-sha256'.";
        }
        container dhGroup {
          presence "";
          description
            "Range of allowed group size, the SSH server responds to the
             client during a 'diffie-hellman-group-exchange'. The range
             will be the intersection of what the client requests, if there
             is none the key exchange will be aborted.";
          leaf minSize {
            must ". <= ../maxSize";
            type dhGroupSizeType;
            default 2048;
            description "Minimal size of p in bits.";
          }
          leaf maxSize {
            type dhGroupSizeType;
            default 4096;
            description "Maximal size of p in bits.";
          }
        }
        leaf mac {
          type string;
          default "";
          description
            "The supported mac algorithms (if implemented in libcrypto) are
             'hmac-md5', 'hmac-sha1', 'hmac-sha2-256', 'hmac-sha2-512',
             'hmac-sha1-96' and 'hmac-md5-96'.";
        }
        leaf encryption {
          type string;
          default "";
          description
            "The supported encryption algorithms (if implemented in libcrypto)
             are 'aes128-ctr', 'aes192-ctr', 'aes256-ctr', 'aes128-cbc',
             'aes256-cbc' and '3des-cbc'.";
        }
      }
      leaf clientAliveInterval {
        type timeoutType;
        default infinity;
        description
          "If no data has been received from a connected client for this
           long, a request that requires a response from the client,
           will be sentover the SSH transport.";
      }
      leaf clientAliveCountMax {
        type uint32;
        default 3;
        description
          "If no data has been received from the client, after this many
           consecutive clientAliveInterval has passed, the connection will be
           dropped.";
      }
    }
    container cli {
      presence "";
      description "CLI parameters.";
      leaf enabled {
        type boolean;
        default true;
        description
          "
           When set to true, the CLI server is started.";
      }
      leaf allowImplicitWildcard {
        type boolean;
        default true;
        description
          "When set to true, users do not need to explicitly type * in the
           place of keys in lists, in order to see all list instances. When
           set to false, users have to explicitly type * to see all list
           instances.";
      }
      leaf startupScriptNonInteractive {
        type boolean;
        default false;
        description
          "startupScriptNonInteractive is either 'true' or 'false'. If
           set to 'true' then a CLI startup script will be evalueated
           also for non-interactive sessions.";
      }
      leaf modeNameStyle {
        type cliModeNameStyleType;
        default short;
        description
          "modeNameStyle is either 'short', 'two', or 'full'. If
           'short', then the mode name of submodes in the Cisco style
           CLIs will be constructed from the last element in the path
           and the instance key. If set to 'two' then the two last
           modes will be used for the mode name. If set to 'full' then
           all components in the path will be used in the mode name.";
      }
      leaf allowOverwriteOnCopy {
        type boolean;
        default false;
        description
          "allowOverwriteOnCopy is either 'true' or 'false'. If set to
           'true' then the copy command in the CLI will overwrite the
           target if it exists. If set to 'false' then an error will
           be displayed if the target exists.";
      }
      leaf inheritPaginate {
        type boolean;
        default true;
        description
          "inheritPaginate is either 'true' or 'false'. If set to
           'true' then the paginate setting of a pipe command will be
           determined by the paginate setting of the main command. If set to
           'false', then the output from a pipe command will not be paginated
           unless pagination for that pipe command has been overridden
           in a clispec file.";
      }
      leaf safeScriptExecution {
        type boolean;
        default true;
        description
          "safeScriptExecution is either 'true' or 'false'. If set to
           'true' then 'exit', 'abort', 'end', and 'commit' are not
           allowed inside a script loaded through maapi with
           maapi_load_config().";
      }
      leaf exitConfigModeOnCtrlC {
        type boolean;
        default true;
        description
          "exitConfigModeOnCtrlC is either 'true' or 'false'. If set to
           'false' the user will not be thrown out of config mode when
           ctrl-c is pressed on an empty command line.";
      }
      leaf execNavigationCmds {
        type boolean;
        default false;
        description
          "execNavigationCmds is either 'true' or 'false'. If set to
           'true' then it is possible to enter a submode also in
           exec mode in C- and I-style CLI.";
      }
      leaf allowOldStyleModeCmds {
        type boolean;
        default false;
        description
          "allowOldStyleModeCmds is either 'true' or 'false'. If set to
           'true' then CLI commands in I and C-style are interpreted
           as mode commands if the path coincide with a dynamic element
           in the data-model. The recommended way to mount commands in
           a submode is instead to use the 'mount' attribute.";
      }
      leaf continueOnErrorCmdStack {
        type boolean;
        default false;
        description
          "continueOnErrorCmdStack is either 'true' or 'false'. If set to
           'true' then command stack execution will continue even if an
           earlier command in the stack failed with an error, ie
              show xx ; show zz
           will execute both 'show xx' and 'show zz' even if 'show xx'
           failed with an error.
           If set to 'false' then command execution will be aborted as
           soon as a command fails.";
      }
      leaf topLevelCmdsInSubMode {
        type boolean;
        default false;
        description
          "topLevelCmdsInSubMode is either 'true' or 'false'. If set
           to 'true' all top level commands in I and C-style CLI are
           available in sub modes.";
      }
      leaf mixedMode {
        type boolean;
        default false;
        description
          "mixedMode is either 'true' or 'false'. If set to 'true'
           all oper mode commands are available in config mode.";
      }
      leaf completionShowOldVal {
        type boolean;
        default true;
        description
          "completionShowOldVal is either 'true' or 'false'. If set to
           'true' a leaf's old value will be displayed inside brackets
           during command line completion. If set to 'false' it will not
           be shown.";
      }
      leaf completionMetaInfo {
        type completionMetaInfoType;
        default false;
        description
          "completionMetaInfo is either 'false', 'alt1' or 'alt2'.
           If set to 'alt1' then the alternatives shown for
           possible completions will be prefixed as follows:

            containers with >
            lists with +
            leaf-lists +

           for example

            Possible completions:
            ...
            > applications
            + apply-groups
            ...
            + dns-servers
            ...

           If set to 'alt2', then possible comopletions will be prefixed
           as follows

            containers with >
            lists with children with +>
            lists without children +

           for example

            Possible completions:
            ...
            > applications
            +>apply-groups
            ...
            + dns-servers
            ...
           This only applies to the J-style CLI.";
      }
      leaf reportInvalidCompletionInput {
        type boolean;
        default true;
        description
          "reportInvalidCompletionInput is either true or false. If
           set to 'true' the CLI will display an error message during
           completion when the user press '?' to indicate if an
           invalid token has been entered on the command line.";
      }
      leaf useShortEnabled {
        type boolean;
        default true;
        description
          "useShortEnabled is either 'true' or 'false'. If set to
           'true' then the CLI will display 'enabled' or 'disabled'
           in place of 'enabled true' and 'enabled false'.";
      }
      leaf smartRenameFiltering {
        type boolean;
        default true;
        description
          "smartRenameFiltering is either 'true' or 'false'. If set to
           'true' then only paths that leads to existing instances
           will be presented when doing completion. This will lead to
           some extra calls to get_next() in order to determine if
           a path has instances or not. When set to 'false' all paths
           with potentialy instances are presented.";
      }
      leaf allowParenQuotes {
        type boolean;
        default false;
        description
          "allowParenQuotes is either 'true' or 'false'. If set to
           'true' then parentheses are treated as quotes, ie the
           string (xx yy) will be equivalent to 'xx yy' and
           xx\\ yy on the CLI command line.";
      }
      leaf singleElemPattern {
        type boolean;
        default true;
        description
          "singleElemPattern is either 'true' or 'false'. If set to
           'true' then a pattern can be used to specify that only
           a single child to a dynamic node should be displayed.";
      }
      leaf multiPatternOperation {
        type multiPatternOperationType;
        default any;
        description
          "multiPatternOperation is one of 'any', and 'all'. When set
           to 'any' a pattern is true if at least one match is found,
           if set to 'all', all patterns needs to be found for the
           pattern expression to be considered true.";
      }
      leaf sortSubmodeCmds {
        type boolean;
        default true;
        description
          "sortSubmodeCmds is either 'true' or 'false'. If set to
           'true' then local submode commands are listed before
           global commands when the user enters ? in a submode
           in C and I-style.";
      }
      leaf sortLocalCmds {
        type boolean;
        default true;
        description
          "sortLocalCms is either 'true' or 'false'. If set to
           'true' and sortSubmodeCmds are also set to true, then
           local submode commands are listed before
           global commands when the user enters ? in a submode
           in C and I-style, and the order of the commands is
           alphabetically ordered. If set to false then the order
           of the local submode commands are the same as in the
           data model.";
      }
      leaf displayEmptyConfigContainers {
        type boolean;
        default true;
        description
          "displayEmptyConfigContainers is either 'true' or 'false'. If set to
           'true' then 'show status' in the J-style CLI will display
           empty dynamic nodes that are not config='false' even when
           there is no data to display. If set to 'false' the those
           containers will not be shown.";
      }
      leaf displayNonPresenceAttributes {
        type boolean;
        default false;
        description
          "displayNonPresenceAttributes is either 'true' or
           'false'. If set to 'true' then all non presence containers
           will display their attributes even if the container is
           empty similar to how presence containers displays its
           attributes. If set to 'false' (default behaviour) those
           attributes will not be shown automatically.";
      }
      leaf showEditors {
        type boolean;
        default true;
        description
          "showEditors is either true or false. If set to true
           then a list of current editors will be displayed when
           a user enters configure mode.";
      }
      leaf whoShowMode {
        type boolean;
        default true;
        description
          "whoShowMode is either 'true' or 'false'. If set to
           'true' then an 'Config Mode' column will be added
           to the table shown when issuing the 'who' command.";
      }
      leaf whoHistoryDateTimeFormat {
        type whoHistoryDateTimeFormatType;
        default short;
        description
          "whoHistoryDateTimeFormat decides if the date should always
           include the date (long), or only include the date when different
           from today (short).";
      }
      leaf editWrapMode {
        type editWrapModeType;
        default wrap;
        description
          "editWrapMode is either 'wrap', 'newline' or 'vt100'.
           If 'wrap' or 'vt100' is
           used then cut-and-paste will work in xterms (and other
           terminal emulators) but the CLI may behave oddly if
           the screen width is manually configured to something
           other than the true screen width.
           If 'vt100' is used then no >space<>backspace<
           sequence
           is used to force line wrapping. This makes it easier for
           scripts that rely on command line echoing but the cursor
           will disappear at the end of the line temporarily.";
      }
      leaf supportQuotedEOL {
        type boolean;
        default true;
        description
          "supportQuoteEOL is either true or false. If set to true
           then a final backslash (\\) on a line means that the next
           line will be concatenated with the previous line, similarly
           to a Linux Shell.";
      }
      leaf allowWildcard {
        type boolean;
        default true;
        description
          "allowWildcard is either 'true' or 'false'. If 'true'
           then wildcard expressions are allowed in show commands.";
      }
      leaf allowAllAsWildcard {
        type boolean;
        default false;
        description
          "Wildcard is normally written as '*' but with 'allowAllAsWildcard'
           set to 'true' the string 'all' will also be accepted in place
           of '*'.";
      }
      leaf allowRangeExpression {
        type boolean;
        default true;
        description
          "allowRangeExpression is either 'true' or 'false'. If 'true'
           then range expressions are allowed for all key values
           of type basic type integer. An alternative is to
           specify hasRange for each path in the clispec.";
      }
      leaf allowRangeExpressionAllTypes {
        type boolean;
        default true;
        description
          "allowRangeExpressionAllTypes is either 'true' or 'false'. If 'true'
           then range expressions are allowed for all key values
           regardless of type. An alternative is to specify hasRange for
           each element in the yang files.";
      }
      leaf useDoubleDotRanges {
        type boolean;
        default false;
        description
          "useDoubleDotRanges is either 'true' or 'false'. If 'true'
           then range expressions are types as 1..3, if set to 'false'
           then ranges are given as 1-3.";
      }
      leaf addExtraTableSpacing {
        type boolean;
        default false;
        description
          "addExtraTableSpacing is either 'true' or 'false'. If
           set to 'true' then an additional newline will be added
           on each side of the table.";
      }
      leaf suppressRangeKeyword {
        type boolean;
        default false;
        description
          "suppressRangeKeyword is either 'true' or 'false'. If 'true'
           then 'range' keyword is not allowed in C- and I-style for
           range expressions.";
      }
      leaf exitModeOnEmptyRange {
        type boolean;
        default false;
        description
          "exitModeOnEmptyRange is either 'true' or 'false'. If 'true' and if
           standing in a range submode, the CLI will exit to the parent
           submode if all instances in the range has been deleted by the user.";
      }
      leaf tableLabel {
        type boolean;
        default false;
        description
          "tableLabel is either 'true' or 'false'. If 'true'
           then tables displayed in C and I style CLI will have
           a relative location label to make it possible to know which
           table is displayed.";
      }
      leaf tableLookAhead {
        type uint64 {
          range "1 .. max";
        }
        default 50;
        description
          "The tableLookAhead element tells confd how many rows to
           pre-fetch when displaying a table. The prefetched rows are
           used for calculating the required column widths for the
           table. If set to a small number it is recommended to explicitly
           configure the column widhts in the clispec file.";
      }
      leaf moreBufferLines {
        type limitType;
        default 5000;
        description
          "moreBufferLines is used to limit the buffering done by the more
           process. It can be 'unbounded' or a possitive integer describing
           the maximum number of lines to buffer.";
      }
      leaf showTableLabelsIfMultiple {
        type boolean;
        default false;
        description
          "showTableLabelsIfMultiple is either 'true' or 'false'.
           If set to 'true' then table labels will only be displayed
           if multiple tables, or a table and additional data is
           displayed. If set to 'false' then table labels are
           always shown if they exists and tableLabel is enabled.";
      }
      leaf defaultTableBehavior {
        type tableBehaviorType;
        default dynamic;
        description
          "defaultTableBehavior is either 'dynamic', 'suppress', or
           'enforce'. If set to 'dynamic' then list nodes will be displayed
           as tables if the resulting table will fit on the screen.
           If set to suppress, then list nodes will not be displayed
           as tables unless a table has been specified by some other
           means (ie through a setting in the clispec-file or through
           a command line parameter), if set to 'enforce' then list
           nodes will always be displayed as tables unless otherwise
           specified in the clispec-file or on the command line.";
      }
      leaf allowTableOverflow {
        type boolean;
        default false;
        description
          "allowTableOverflow is either 'true' or 'false'. If 'true'
           then tables displayed in a Cisco style CLI will be allowed
           to overflow.  If 'false' a too wide table will be displayed
           as a 'setting - value' list instead.";
      }
      leaf tableOverflowTruncate {
        type boolean;
        default false;
        description
          "tableOverflowTruncate is either 'true' or 'false'. If 'true'
           then overflowing tables will be truncated instead of wrapped.";
      }
      leaf allowTableCellWrap {
        type boolean;
        default true;
        description
          "allowTableCellWrap is either 'true' or 'false'. If 'true'
           then tables displayed in a Cisco style CLI will be allowed
           to wrap if the initial cell-width estimate proves to be too
           narrow.  If 'false' a too wide table cell will overflow
           instead, pushing the rest of the line to the right.";
      }
      leaf showAllNs {
        type boolean;
        default false;
        description
          "showAllNs is either 'true' or 'false'. If 'true' then all
           element names will be shown with their namespace prefix in
           the CLI. This is visible when displaying the running
           configuration and when modifying the configuration.";
      }
      leaf useExposeNsPrefix {
        type boolean;
        default true;
        description
          "useExposeNsPrefix is either 'true' or 'false'. If 'true' then all
           nodes annotated with the tailf:cli-expose-ns-prefix will
           result in the namespace prefix being shown/required.
           If set to 'false' then the tailf:cli-expose-ns-prefix annotation
           will be ignored.";
      }
      leaf orderedShowConfig {
        type boolean;
        default true;
        description
          "orderedShowConfig is either 'true' or 'false'. If 'true' then
           the commands displayed when running the 'show configuration'
           command in C-mode will take leafrefs and cli-diff-dependency
           into account.";
      }
      leaf suppressFastShow {
        type boolean;
        default false;
        description
          "suppressFastShow is either 'true' or 'false'. If 'true' then
           the fast show optimization will be suppressed in the
           C-style CLI. The fast show optimization is somewhat
           experimental and may break certain operations.";
      }
      leaf leafPrompting {
        type boolean;
        default true;
        description
          "leafPrompting is either 'true' or 'false'. If 'true' the CLI will
           prompt the user for leaf values if they are not provided on the
           command line. If 'false' then an error message will be displayed
           if the user does not provide a value for a leaf.";
      }
      leaf modeInfoInAudit {
        type modeInfoInAuditType;
        default false;
        description
          "modeInfoInAudit is either 'true', 'false' or 'path'. If 'true',
           then all commands will be prefixed with major and minor mode
           name when logged as audit messages. This means that it is
           possible to differentiate between commands with the same
           name in different modes. Major mode is 'operational' or
           'configure' and minor mode is 'top' in J-style and the name
           of the submode in C- and I-mode. On the top-level in C- and
           I-mode it is also 'top'. If set to 'path' the major mode
           will be followed by the full command path to the submode.";
      }
      leaf auditLogMode {
        type cliAuditLogType;
        default all;
        description
          "auditLogMode is either 'all', 'allowed', or 'denied'. If
           'all', then all commands that the user tries to execute will
           be logged in the audit trail log. If 'allowed', only allowed
           commands will be logged, ie commands that are actually run
           by the user. If 'denied', only commands that the user were
           not allowed to execute will be logged, prefixed with
           'denied'.";
      }
      leaf transactions {
        type boolean;
        default true;
      }
      leaf transactionCtrlCmds {
        type boolean;
        default false;
        description
          "transactionCtrlCmds is either 'true' or 'false'. If
           'true', then the CLI will have commands for enabling
           and disabling transactions in configure mode, ie
           'enable transactions' and 'disable transactions'.
           If set to 'false' no such commands will be present.";
      }
      leaf style {
        type cliStyle;
        default j;
        description
          "style is either 'j', 'c', or 'i'. If 'j', then the CLI will
           be presented as a Juniper style CLI. If 'c' then the CLI
           will appear as Cisco XR style, and if 'i' then a Cisco IOS
           style CLI will be rendered.";
      }
      leaf completionShowMax {
        type cliMax;
        default 100;
        description
          "Maximum number of possible alternatives to present when
           doing completion.";
      }
      leaf rollbackAAA {
        type boolean;
        default false;
        description
          "If set to true then AAA rules will be applied when a
           rollback file is loaded. This means that rollback may
           not be possible if some other user have made changes
           that the current user does not have access privileges
           to.";
      }
      leaf rollbackMax {
        type rollMax;
        default 1000;
        description
          "Maximum number of possible alternatives to present when
           doing rollback.";
      }
      leaf rollbackNumbering {
        type rollNumbering;
        default rolling;
        description
          "rollbackNumbering is either 'fixed' or 'rolling'. If set
           to 'rolling' then rollback file '0' will always contain the
           last commit. When using 'fixed' each rollback will get
           a unique increasing number.";
      }
      leaf rollbackNumberingInitial {
        type int64;
        default 10000;
        description
          "rollbackNumberingInitial is the starting point of the rollback
           numbering when the 'increasing' rollback numbering scheme is
           used.";
      }
      leaf inconsistentDatabaseSuffix {
        type string;
        default "";
        description
          "The inconsistentDatabaseSuffix is a message that is appended
           to the warning message that the CLI displays when it detects
           that the running database have got inconsistent.";
      }
      leaf showDefaults {
        type boolean;
        default false;
        description
          "showDefaults is either 'true' or 'false'. If 'true' then
           default values will be shown when displaying the
           configuration. The default value is shown inside a comment
           on the same line as the value. Showing default values can
           also be enabled in the CLI per session using the operational
           mode command 'set show defaults true'.";
      }
      leaf reallocateOperTrans {
        type boolean;
        default false;
        description
          "reallocateOperTrans is either 'true' or 'false'. If 'true' then
           a new read transaction will be allocated for each oper-mode
           command. When set to 'false' a single oper transaction will
           be used for the entire  CLI session.";
      }
      leaf quickSshTeardown {
        type boolean;
        default false;
        description
          "quickSshTeardown controls if CLI sessions initiated through
           an SSH sessions should be torn down directly when the socket
           is closed, or not. When set to 'true' the socket will be closed
           as soon as the CLI receives a tcp shutdown, if set to 'false'
           it will wait until all pending data has been written.";
      }
      leaf cAlignLeafValues {
        type boolean;
        default true;
        description
          "cAlignLeafValues is either 'true' or 'false'. If 'true' then
           the leaf values of all siblings in a container or list will
           be aligned.";
      }
      leaf jAlignLeafValues {
        type boolean;
        default true;
        description
          "jAlignLeafValues is either 'true' or 'false'. If 'true' then
           the leaf values of all siblings in a container or list will
           be aligned.";
      }
      leaf defaultPrefix {
        type string;
        default "";
        description
          "defaultPrefix is a string that is placed in front of the
           default value when a configuration is shown with default
           values as comments.";
      }
      leaf jWarningPrefix {
        type string;
        default "Warning: ";
        description
          "jWarningPrefix is a string that is placed in front of warnings
           when they are displayed in the CLI. J-style CLI.";
      }
      leaf jAbortedPrefix {
        type string;
        default "Aborted: ";
        description
          "jAbortedPrefix is a string that is placed in front of aborted
           messages when they are displayed in the CLI. J-style CLI.";
      }
      leaf jErrorPrefix {
        type string;
        default "Error: ";
        description
          "jErrorPrefix is a string that is placed in front of error
           messages when they are displayed in the CLI. J-style CLI.";
      }
      leaf cWarningPrefix {
        type string;
        default "Warning: ";
        description
          "cWarningPrefix is a string that is placed in front of warnings
           when they are displayed in the CLI. I- and C-style CLI.";
      }
      leaf cAbortedPrefix {
        type string;
        default "Aborted: ";
        description
          "cAbortedPrefix is a string that is placed in front of aborted
           messages when they are displayed in the CLI. I- and C-style CLI.";
      }
      leaf cErrorPrefix {
        type string;
        default "Error: ";
        description
          "cErrorPrefix is a string that is placed in front of error
           messages when they are displayed in the CLI. I- and C-style CLI.";
      }
      leaf invalidDataString {
        type string;
        default --ERROR--;
        description
          "invalidDataString is a string that is displayed instead of
           the real value whenever a data provider returns an invalid
           data element.";
      }
      leaf showKeyName {
        type boolean;
        default true;
        description
          "showKeyName controls if the name of the key should be
           shown in the type string during completion.";
      }
      leaf commitRetryTimeout {
        type timeoutType;
        default PT0S;
        description
          "Commit timeout in the CLI. This timeout controls for how
           long the commit operation will attempt to complete the
           operation when some other entity is locking the database,
           e.g. some other commit is in progress or some managed
           object is locking the database.

           There is a similiar configuration parameter,
           /confdConfig/commitRetryTimeout, which sets a timeout for all
           ConfD transactions, not just for CLI transactions.";
      }
      leaf timezone {
        type cliTimezoneType;
        default local;
        description
          "Time in the CLI can be either local, as configured on
           the device, or UTC.";
      }
      leaf utcOffset {
        type int64;
        default 0;
        description
          "If the timezone is set to UTC this can be set to
           specify the UTC offset measured in minutes.";
      }
      leaf oldDetailsArg {
        type boolean;
        default false;
        description
          "oldDetailsArg is either 'true' or 'false'. If 'false' then
           commands that display the configuration will not have a
           'details' argument but instead have a pipe flag called
           'details'. The setting is present for backwards compatability,
           the recommended setting for future use is 'false'.";
      }
      leaf withDefaults {
        type boolean;
        default false;
        tailf:info "DEPRECATED - use defaultHandlingMode instead";
        description
          "DEPRECATED - use /confdConfig/defaultHandlingMode instead
           to control this behavior consistently for all northbound
           interfaces.

           withDefaults is either 'true' or 'false'. If 'false' then
           leaf nodes that have their default values will not be shown
           when the user displays the configuration, unless the user
           gives the 'details' option to the 'show' command.

           This is useful when there are many settings which are seldom
           used. When set to 'false' only the values actually modified
           by the user will be shown.";
      }
      leaf ignoreShowWithDefaultOnDiff {
        type boolean;
        default false;
        description
          "When set to 'true' ConfD will ignore the annotation
           tailf:cli-show-with-default when displaying the
           configuration changes in the C-style CLI.";
      }
      leaf trimDefaultShow {
        type boolean;
        default false;
        description
          "trimDefaultShow is either 'true' or 'false'. If 'true' then
           leaf nodes that have the same value as the default value will
           not be displayed even when explicitly configured to have that
           value. When set to 'false' such leaves will be displayed if
           explicitly configured to have the value. This setting applies
           to show commands, ie show running-config and show config.";
      }
      leaf trimDefaultSave {
        type boolean;
        default false;
        description
          "trimDefaultSave is either 'true' or 'false'. If 'true' then
           leaf nodes that have the same value as the default value will
           not be displayed even when explicitly configured to have that
           value. When set to 'false' such leaves will be displayed if
           explicitly configured to have the value. This setting applies
           to the save command.";
      }
      leaf banner {
        type string;
        default "";
        description
          "Banner shown to the user when the CLI is started. Default is
           empty.";
      }
      leaf bannerFile {
        type string;
        default "";
        description
          "Banner file containing a banner shown to the user when the
           CLI is started. Default is empty.";
      }
      leaf prompt1 {
        type string;
        default "\\u@\\h\\M> ";
        description
          "Prompt used in operational mode. The string may contain a
           number of backslash-escaped special characters which are
           decoded as follows:
           \\d
              the date in 'YYYY-MM-DD' format (e.g., '2006-01-18')
           \\h
              the hostname up to the first '.' (or delimiter as defined
              by promptHostnameDelimiter)
           \\H
              the hostname
           \t
              the current time in 24-hour HH:MM:SS format
           \\T
              the current time in 12-hour HH:MM:SS format
           \\@
              the current time in 12-hour am/pm format
           \\A
              the current time in 24-hour HH:MM format
           \\u
              the username of the current user
           \\m
              the mode name (only used in XR style)
           \\M
              the mode name inside parenthesis if in a mode";
      }
      leaf prompt2 {
        type string;
        default "\\u@\\h\\M% ";
        description
          "Prompt used in configuration mode. The string may contain a
           number of backslash-escaped special characters which are
           decoded as described for prompt1.";
      }
      leaf cPrompt1 {
        type string;
        default "\\h\\M# ";
        description
          "Prompt used in operational mode in C style. The string may
           contain a number of backslash-escaped special characters
           which are decoded as described above.";
      }
      leaf cPrompt2 {
        type string;
        default "\\h(\\m)# ";
        description
          "Prompt used in configuration mode in C style. The string may
           contain a number of backslash-escaped special characters
           which are decoded as described above.";
      }
      leaf cStylePromptInJStyle {
        type boolean;
        default false;
        description
          "If set to true then the \\m and \\M will be expandes just as in C-
           and I-style";
      }
      leaf promptHostnameDelimiter {
        type string;
        default ".";
        description
          "When the \\h token is used in a prompt the first part of
           the hostname up until the first occurance of the
           promptHostnameDelimiter is used.";
      }
      leaf asyncPromptRefresh {
        type boolean;
        default true;
        description
          "asyncPromptRefresh is either 'true' or 'false'. If set to
           'true' the CLI prompt will be refreshed when asynchronous
           tasks prints messages in the CLI, such as messages from
           other users.";
      }
      leaf showLogDirectory {
        type string;
        default "/var/log";
        description
          "Location where the 'show log' command looks for log files.";
      }
      leaf idleTimeout {
        type xs:duration;
        default PT30M;
        description
          "Maximum idle time before terminating a CLI session. Default
           is PT30M, ie 30 minutes.";
      }
      leaf promptSessionsCLI {
        type boolean;
        default false;
        description
          "promptSessionsCLI is either 'true' or 'false'. If set to 'true'
           then only the current CLI sessions will be displayed when the user
           tries to start a new CLI session and the maximum number of sessions
           has been reached. Note that MAAPI sessions with their context set to
           'cli' would be regarded as CLI sessions and would be listed as
           such.";
      }
      leaf disableIdleTimeoutOnCmd {
        type boolean;
        default true;
        description
          "disableIdleTimeoutOnCmd is either 'true' or 'false'. If
           set to 'false' then the idle timeout will trigger even
           when a command is running in the CLI. If set to 'true'
           the idle timeout will only trigger if the user is idling
           at the CLI prompt.";
      }
      leaf commandTimeout {
        type timeoutType;
        default infinity;
        description
          "Global command timeout. Terminate command unless the command
           has completed within the timeout. It is generally a bad idea
           to use this feature since it may have undesirable effects in
           a loaded system where normal commands take longer to
           complete than usual.

           This timeout can be overridden by a command specific timeout
           specified in the confd.cli file.";
      }
      container spaceCompletion {
        presence "";
        description
          "Default value for space completion in the CLI. The user can
           always enable or disable completion on space, this only
           controls the initial session value.";
        leaf enabled {
          type boolean;
          default true;
          description
            "enabled is either 'true' or 'false'. If 'true' command and
             argument completion will be performed when <space>
             is entered.";
        }
      }
      container timestamp {
        presence "";
        description
          "Default value for the timestamps in the CLI.
           The user can always enable or disable the display of timestamps,
           this only controls the initial session value.";
        leaf enabled {
          type boolean;
          default false;
          description
            "enabled is either 'true' or 'false'. If 'true' the CLI will
             print a timestamp before the output of each command.";
        }
        leaf clock24 {
          type boolean;
          default true;
          description
            "clock24 is either 'true' or 'false'. If 'true' the 24-hour
             time notation wil be used when displaying hours.";
        }
        leaf format {
          type string;
          default
            '\d{l,4}\m{l,5}\D{l,3}\H{r,2,0}:'
          + '\t{r,2,0}:\s{r,2,0}.\c{l,3,0}'
          + ' UTC\u{l,1}\o{r,2,0}:\k{r,2,0}';
          description
            "Specifies the format of the timestamp. The string may contain a
             number of backslash-escaped special characters which are
             decoded as follows:
             \\Y
              the current year (YYYY)
             \\M
              the current month (1-12)
             \\D
              the current day of month (1-31)
             \\m
              the name of the current month (Jan, Feb, ...)
             \\d
              the name of the current day of week (Mon, Tue, ...)
             \\H
              the current hour (0-23 or 1-12)
             \t
              the current minute (0-59)
             \\a
              am/pm (available only in 12-hour notation)
             \\A
              AM/PM (available only in 12-hour notation)
             \\s
              the current second (0-59)
             \\c
              the current microsecond (0+)
             \\u
              UTC offset sign (-/+)
             \\o
              UTC offset hour (0-23 or 1-12)
             \\k
              UTC offset minute (0-59)
             NOTE: the UTC offset characters \\u, o and \\k
             can still be used even if the timezone
             (/confdConfig/cli/timezone) is set to 'local'.
             The characters \\a (am/pm) and \\A (AM/PM) should only be used when
             clock24 (/confdConfig/cli/timestamp/clock24) is set to 'false'.

             After each special character another character sequence can be
             specified in order to control the field width, alignment and
             padding character. The sequence can be either {A, W, P} or
             {A,W} where A is the alignment and can be either 'l' or 'r',
             W is the field width and P is the padding character. If P is not
             specified, ' ' will be used as the padding character.
             Example, the format '\\d{l,4}\\m{l,5}\\D{l,3}\\H{r,2,0}:\\t{r,2,0}'
             would translate into 'Wed Jun  3  08:35'.";
        }
      }
      container autoWizard {
        presence "";
        description
          "Default value for autowizard in the CLI. The user can always
           enable or disable the auto wizard in each session, this
           controls the initial session value.";
        leaf enabled {
          type boolean;
          default true;
          description
            "enabled is either 'true' or 'false'. If 'true' the CLI
             will prompt the user for required attributes when a new
             identifier is created.";
        }
      }
      container ssh {
        presence "";
        leaf enabled {
          type boolean;
          default true;
          description
            "enabled is either 'true' or 'false'. If 'true' ConfD will
             will use the built in SSH server.";
        }
        leaf ip {
          type inet:ip-address;
          default "0.0.0.0";
          description
            "ip is an IP address which the ConfD CLI should listen to
             for SSH sessions. 0.0.0.0 means that it listens to the
             port (/confdConfig/cli/ssh/port) for all IPv4
             addresses on the machine.";
        }
        leaf port {
          type inet:port-number;
          default 2024;
          description "The port number for CLI SSH";
        }
        leaf-list extraIpPorts {
          type xs:token;
          description
            "extraIpPorts is a leaf-list of ip:port
             pairs which the CLI also listens to for SSH connections.";
        }
        leaf dscp {
          type dscpType;
          description
            "Support for setting the Differentiated Services Code Point
             (6 bits) for traffic originating from the CLI
             for SSH connections.";
        }
        leaf banner {
          type string;
          default "";
          description
            "banner is a string that will be presented to the client
             before authenticating when logging in to the CLI via the
             built-in SSH server.";
        }
        leaf bannerFile {
          type string;
          default "";
          description
            "Name of file whose contents will be presented to the client
             before authenticating when logging in to the CLI via the
             built-in SSH server.
             If ../banner is non-empty, the contents of the file will
             be appended to the value of ../banner.";
        }
      }
      leaf commitMessage {
        type boolean;
        default true;
        description
          "commitMessage is either 'true' or 'false'. If set to
           'true' then a message will be displayed in the CLI
           whenever a commit operation is performed in the system.
           This is always disabled in I-style, and in transactionless
           mode.";
      }
      leaf commitMessageFormat {
        type string;
        default
          '\nSystem message at $(time)...\n'
        + 'Commit performed by $(user) via $(proto) using $(ctx).\n';
        description
          "commitMessageFormat controls how commit messages are
           displayed in the CLI. The format
           string may contain the variables $(user), $(time), $(ctx),
           $(date), $(time12), $(time12ampm), $(time12hm), $(host),
           $(hostname), and $(proto).";
      }
      container suppressCommitMessages {
        presence "";
        leaf-list context {
          type string;
          description
            "Suppress commit messages from certain contexts, such as system.";
        }
      }
      leaf jShowCR {
        type boolean;
        default false;
        description
          "jShowCR is either 'true' or 'false'. If set to
           'true' then the J-style CLI will show >cr< in
           the completion list whenever it is legal to press cr.";
      }
      leaf showPipe {
        type boolean;
        default true;
        description
          "showPipe is either 'true' or 'false'. If set to 'true' the
           completion list will contain | in operational mode if it
           is legal to enter |. In J-style the jShowCR must also be
           set to enable this. If disablePipe is set to 'true', it
           will override the setting of showPipe and imply the same
           behavior as if showPipe is 'false'.";
      }
      leaf showPipeConfig {
        type boolean;
        default false;
        description
          "showPipeConfig is either 'true' or 'false'. If set to
           'true' the completion list will contain | in configure
           mode if it is legal to enter |. In J-style the jShowCR
           must also be set to enable this. If disablePipeConfig is
           set, to 'true', it will override the setting of
           showPipeConfig and imply the same behavior as if
           showPipeConfig is 'false'.";
      }
      leaf disablePipe {
        type boolean;
        default false;
        description
          "disablePipe is either 'true' or 'false'. If set to 'true'
           then the pipe commands are disabled in operational mode.";
      }
      leaf disablePipeConfig {
        type boolean;
        default false;
        description
          "disablePipeConfig is either 'true' or 'false'. If set to
           'true' then the pipe commands are disabled in configure
           mode.";
      }
      leaf pipeHelpMode {
        type pipeHelpModeType;
        default auto;
        description
          "If showPipe is set to true, then pipeHelpMode determines
           how the pipe option will be displayed to the user. If set
           to 'auto', then the description text 'Output modifiers' will
           only be displayed if there are any other options with help
           texts, otherwise it will not be shown. If set to 'always' then
           the help text will always be displayed, if set to 'never'
           then it will never be displayed.";
      }
      leaf jAllowDeleteAll {
        type boolean;
        default true;
        description
          "jAllowDeleteAll is either 'true' or 'false'. If set to
           'true' then the J-style CLI will show the command 'delete'
           without argumets, if set to 'false' then an argument
           is required.";
      }
      leaf cSilentNo {
        type boolean;
        default true;
        description "Silently ignore deletes of non-existing instances.";
      }
      leaf noFollowIncompleteCommand {
        type boolean;
        default false;
        description
          "noFollowIncompleteCommand is either 'true' or 'false'. If set to
           'true' then the 'no' command will take incomplete-command
           declarations into account. If set to 'false' it will not.";
      }
      leaf cRestrictiveNo {
        type boolean;
        default false;
        description
          "If a leaf value is given when an optional leaf is deleted,
           the given value is normally ignored and the node is deleted
           regardless of the value. When cRestrictiveNo is set to
           'true', the given value is required to be equal to the old
           value in order to the delete operation to be allowed.";
      }
      leaf prioritizeSubmodeCmds {
        type boolean;
        default true;
        description
          "prioritizeSubmodeCmds is either 'true' or 'false'. If set to
           'true' then local submode commands are prioritized before
           commands in parent (and grand-parent) modes in C and
           I-style. This means that if a command in local submode is
           ambiguous with a command in parent (or grand-parent) mode
           the local submode command is executed. See also
           cExtendedCmdSearch.";
      }
      leaf cExtendedCmdSearch {
        type boolean;
        default true;
        description
          "Extend the available submode commands to all commands in
           parent (and grand-parent) modes. These commands are not
           visible during completion but will be executed if entered.
           If set to 'false' then only commands for entering other
           submodes are available in parent and grand-parent modes,
           if set to 'true' all commands in parent and grand-parent
           modes are available.";
      }
      leaf cSuppressCmdSearch {
        type boolean;
        default false;
        description
          "Prevent non-local commands from being executed. This
           negates the effect of cExtendedCmdSearch above. It is
           recommended to also set cModeExitFormat to 'exit' when
           this option is set to true.";
      }
      leaf enterSubmodeOnLeaf {
        type boolean;
        default true;
        description
          "enterSubmodeOnLeaf is either 'true' or 'false'. If set
           to 'true' (the default) then setting a leaf in a submode
           from a parent mode results in entering the submode after
           the command has completed. If set to 'false' then an
           explicit command for entering the submode is needed.
           For example, if running the command

             interface FastEthernet 1/1/1 mtu 1400

           from the top level in config mode. If enterSubmodeOnLeaf
           is true the CLI will end up in the 'interface FastEthernet
           1/1/1' submode after the command execution. If set to
           'false' then the CLI will remain at the top level.
           To enter the submode when set to 'false' the command

             interface FastEthernet 1/1/1

           is needed.
           Applied to the C- and I- style CLI.";
      }
      leaf jExtendedShow {
        type boolean;
        default true;
        description
          "jExtendedShow is either 'true' or 'false'. If set to
           'true' then the J-style CLI will have auto-rendered
           show commands in the same style as the C and I-style
           CLIs. The 'show status' command can still be used for
           viewing config='false' data.";
      }
      leaf jShowUnset {
        type boolean;
        default false;
        description
          "jShowUnset is either 'true' or 'false'. If set to
           'true' then the J-style CLI will show unset leaves
           with the value of jShowUnsetText when doing 'show configuration'.";
      }
      leaf jShowUnsetText {
        type string;
        default UNSET;
        description
          "jShowUnsetText is the text printed for unset values
           if jShowUnset has been set to true.";
      }
      leaf jStatusFormat {
        type string;
        default "[$(status)][$(time)]\\n";
        description
          "jStatusFormat controls which status message is displayed
           after executing a CLI command in the J-style CLI. The format
           string may contain the variables $(status), $(time),
           $(date), $(time12), $(time12ampm), $(time12hm), $(host),
           $(hostname), and $(proto).";
      }
      leaf cModeExitFormat {
        type string;
        default !;
        description
          "cModeExitFormat is the string used in the CLI when
           displaying the running configuration to indicate
           exit from a submode.";
      }
      leaf forcedExitFormat {
        type string;
        default "\\nYou are forced out of configure mode by $(sender).\\n";
        description
          "forceExitFormat controls which message to display when
           a user is forced out of configure mode by another user. The format
           string may contain the variables $(user), $(time),
           $(date), $(time12), $(time12ampm), $(time12hm), $(host) and
           $(hostname).";
      }
      leaf showSubsystemMessages {
        type boolean;
        default true;
        description
          "showSubsystemMessages is either 'true' or 'false'. If 'true'
           the CLI will display a system message whenever a connected
           daemon is started or stopped.";
      }
      leaf ignoreSubsystemFailures {
        type boolean;
        default false;
        description
          "ignoreSubsystemFailures is either 'true' or 'false'. If
           'true' the CLI will make a best effort to display data
           even if a data provider is unavailable.";
      }
      leaf showEmptyContainers {
        type boolean;
        default false;
        description
          "showEmptyContainers is either 'true' or 'false'. If 'true'
           the CLI will display empty container nodes when displaying
           the configuration.  If 'false' then empty static containers
           will not be shown.";
      }
      leaf showTags {
        type boolean;
        default true;
        description
          "showTags is either 'true' or 'false'. If 'true'
           the CLI will display configuration tags if they are present.
           If set to 'false' then the tags will not be displayed by
           default.";
      }
      leaf showAnnotations {
        type boolean;
        default true;
        description
          "showAnnotations is either 'true' or 'false'. If 'true'
           the CLI will display configuration annotations if they are present.
           If set to 'false' then the annotations will not be displayed by
           default.";
      }
      leaf showServiceMetaData {
        type boolean;
        default false;
      }
      leaf suppressNedErrors {
        type boolean;
        default false;
      }
      leaf jShowTableRecursive {
        type boolean;
        default false;
        description
          "jShowTableRecursive is either 'true' or 'false'. If 'true' the
           J-style CLI will attempt to display the result of the command
           'show table' as a table even when a dynamic node is not directly
           specified. If set to 'false' then a table will only be produced
           if a dynamic node is specified as argument to 'show table'.";
      }
      leaf cPrivate {
        type boolean;
        default false;
        description
          "cPrivate is either 'true' or 'false'. If set to 'true' then
           the term 'private' will be used in place of 'terminal' for
           denoting the private/terminal configuration mode. When set
           to 'false' the term 'terminal' will be used instead.";
      }
      leaf cTab {
        type boolean;
        default false;
        description
          "cTab is either 'true' or 'false'. If 'true' the Cisco style
           CLI will not display any help text when the user enters TAB.
           If 'false' then help text will be shown when entering TAB,
           similarly to the Juniper-style CLI.";
      }
      leaf cTabInfo {
        type boolean;
        default false;
        description
          "cTabInfo is either 'true' or 'false'. If 'false' the Cisco
           style CLI will not display any info text when the user
           enters TAB. If 'true' then info text will be shown when
           entering TAB, similarly to the Juniper-style CLI.";
      }
      leaf tabExtend {
        type boolean;
        default true;
        description
          "tabExtend is either 'true' or 'false'. If 'true' the CLI will
           extend the current token to the next longer alternative.";
      }
      leaf cHelp {
        type boolean;
        default true;
        description
          "cHelp is either 'true' or 'false'. If 'true' the Cisco style
           CLI will not display any desc text when the user enters
           '?'.  If 'false' then desc text will be shown when entering
           '?', similarly to the Juniper-style CLI.";
      }
      leaf jHideHelp {
        type boolean;
        default false;
        description
          "jHideHelp is either 'true' or 'false'. If 'true' the
           Juniper style CLI will not display any desc text when the
           user enters '?'.  If 'false' then desc text will be shown
           when entering '?'.";
      }
      leaf restrictedFileAccess {
        type boolean;
        default false;
        description
          "restrictedFileAccess is either 'true' or 'false'. If 'true'
           then a CLI user will not be able to access files and
           directories outside the home directory tree.";
      }
      leaf hideDotFiles {
        type boolean;
        default false;
        description
          "hideDotFile is either 'true' or 'false'. If 'true'
           then files starting with a '.' will not be visible in
           the CLI.";
      }
      leaf restrictedFileRegexp {
        type string;
        default "";
        description
          "restrictedFileRegexp is either an empty string or an regular
           expression (AWK style). If not empty then all files and
           directories created or accessed must match the regular
           expression. This can be used to ensure that certain symbols
           does not occur in created files.";
      }
      leaf historySave {
        type boolean;
        default true;
        description
          "If set to 'true' then the CLI history will be saved
           between CLI sessions. The history is stored in the
           state directory.";
      }
      leaf historyRemoveDuplicates {
        type boolean;
        default false;
        description
          "If set to 'true' then repeated commands in the CLI will only
           be stored once in the history. Each invocation of the
           command will only update the date of the last entry. If set
           to 'false' duplicates will be stored in the history.";
      }
      leaf historyMaxSize {
        type int64;
        default 1000;
        description "Sets maximum configurable history size.";
      }
      leaf messageMaxSize {
        type int64;
        default 10000;
        description "Maximum size of user message.";
      }
      leaf mapActions {
        type cliActionMapType;
        default both;
        description
          "Display data model actions in operational mode, configure
           mode, or both in C and I style CLIs.";
      }
      leaf compactTable {
        type boolean;
        default true;
        description "Display tables in compact mode.";
      }
      leaf compactShow {
        type boolean;
        default false;
        description
          "Use compact representation when showing the configuration in
           C and I style CLIs.";
      }
      leaf compactStatsShow {
        type boolean;
        default false;
        description
          "Use compact representation when showing the operational data
           in C and I style CLIs.";
      }
      leaf prettifyStatsName {
        type boolean;
        default false;
        description
          "Default setting for prettifying, ie changing _ and - to space
           in element names when displaying config='false' data in key-value
           listings.";
      }
      leaf showCommitProgress {
        type boolean;
        default false;
        description
          "showCommitProgress can be either 'true' or 'false'. If set to
           'true' then the commit operation in the CLI will provide
           some progress information.";
      }
      leaf commitActivityClock {
        type boolean;
        default false;
        description
          "commitActivityClock can be either 'true' or 'false'. If set to
           'true' then a |/-\\| style animation will be displayed if
           the commit operation takes more than 200 ms to complete.";
      }
      leaf confirmUncommitedOnExit {
        type confirmUncommitedOnExitType;
        default prompt;
        description
          "If set to 'prompt' then the user will be prompted whether
           to discard uncommitted changes or not. If set to 'discard'
           then uncommitted changes will be discarded without
           prompting the user. If set to 'commit' then uncommitted
           changes will be automatically committed without asking the
           user.";
      }
      leaf reconfirmHidden {
        type boolean;
        default false;
        description
          "If set to true the user will have to re-confirm non-echoing
           values in the CLI. Ie, when the CLI prompts the user for a
           value that is not echoed the user will be asked to enter it
           twice.";
      }
      leaf dequoteHidden {
        type boolean;
        default false;
        description
          "If set to true the value that the user entered will be
           dequoted, ie if the user enters \\n it will be interpreted
           as a newline. This is the default behavior for all other
           leaf types. If set to false then no unquoting will be
           performed for hidden (non-echoing) data types when the
           CLI explicitly prompts for their values. Dequoting will
           still be performed for values entered directly on the
           command line.";
      }
      leaf enumKeyInfo {
        type boolean;
        default false;
        description
          "If set to true the CLI will add the text
           <keyname:enumeration> whenever it is displaying a
           completion list for entering a key value that is an
           enumeration. For example:

           io(config)# vqe dsp channel 1
           Possible completions:
           <b-id:enumeration>  10  11  12  13  14  5  6  9";
      }
      leaf columnStats {
        type boolean;
        default false;
        description
          "columnStats is either 'true' or 'false'. If 'false' then the
           container element is repeated on each line when displaying
           config='false' data in the C and I style CLIs using the
           'show' command. If set to 'true' then the name of the
           container will not be repeated, instead all leaves will be
           indented.";
      }
      leaf allowAbbrevCmds {
        type boolean;
        default true;
        description
          "allowAbbrevCmds is either 'true' or 'false'. If 'false' then
           commands are not allowed to be abbrevated in the CLI.";
      }
      leaf allowAbbrevCmdsOnLoad {
        type boolean;
        default true;
        description
          "allowAbbrevCmdsOnLoad is either 'true' or 'false'. If 'false' then
           commands are not allowed to be abbrevated in the CLI in non
           interactive mode, ie when loading configurations from file.";
      }
      leaf allowAbbrevKeys {
        type boolean;
        default false;
        description
          "allowAbbrevKeys is either 'true' or 'false'. If 'false' then
           key elements are not allowed to be abbrevated in the
           CLI. This is relevant in the J-style CLI when using the
           commands 'delete' and 'edit'. In the C/I-style CLIs when
           using the commands 'no', 'show configuration' and for
           commands to enter submodes.";
      }
      leaf allowAbbrevParamNames {
        type boolean;
        default false;
        description
          "allowAbbrevParamNames is either 'true' or 'false'. If
           'false' then cli command parameter names, ie
           <name>xx</name>, cannot be abbrevated.";
      }
      leaf allowAbbrevEnums {
        type boolean;
        default true;
        description
          "allowAbbrevEnums is either 'true' or 'false'. If 'false'
           then enums entered in the cli cannot be abbrevated.";
      }
      leaf allowCaseInsensitiveEnums {
        type boolean;
        default true;
        description
          "allowCaseInsensitiveEnums is either 'true' or 'false'. If
           'false' then enums entered in the cli must match in case, ie
           you cannot enter FALSE if the cli asks for 'true' or
           'false'.";
      }
      leaf strictRefsOnLoad {
        type boolean;
        default false;
        description
          "strictRefsOnLoad is either 'true' or 'false'. If 'false' then
           keyref/leafref targets does not have to exist when loading
           a config from a file. If set to 'true' then the target creation
           must appear earlier in the loaded file than the reference to the
           target. Note that there is a rather heavy performance penalty
           for loading files with many keyrefs when this is set to true,
           or for piping CLI commands into confd_cli.";
      }
      leaf stopLoadOnError {
        type boolean;
        default true;
        description
          "stopLoadOnError is either 'true' or 'false'. If 'false' then
           the 'load' command in the C and I-style CLIs will not terminate
           on the first error but continue to process commands form
           the file.";
      }
      leaf allOrNothingLoad {
        type boolean;
        default false;
        description
          "allOrNothingLoad is either true or false. If set to true
           then the transaction will be reset and all changes discarded
           if an error is encountered when loading a file. This behavior
           will not happen when the 'best effort' pipe target is used,
           nor when stopLoadOnError is set to false, nor when
           autocommitLoad is set to true.";
      }
      leaf autocommitLoad {
        type boolean;
        default false;
        description
          "autocommitLoad is either 'true' or 'false'. If 'true' then
           when executing the 'load' command each line will be committed
           as soon as it has been read. Note that this is normally not a good
           idea. Only applies when transactions are disabled.";
      }
      leaf autocommitLoadChunkSize {
        type uint64 {
          range "1 .. max";
        }
        default 1;
        description
          "autocommitLoadChunkSize is used to avoid auto commit:ing
           after each line but instead commit after a chunk of lines
           have been read.";
      }
      leaf enableLoadMerge {
        type boolean;
        default true;
        description
          "enableLoadMerge is either 'true' or 'false'. If 'false' then
           the 'load' command in the C and I-style CLIs will not have
           an option for how to load a config file. If set to 'true'
           then the 'load' command will have an additional option for
           loading the file either in 'override' mode or in 'merge'
           mode. 'override' is the mode used if enableLoadMerge is set
           to 'false'.";
      }
      leaf loadActivityClock {
        type boolean;
        default false;
        description
          "loadActivityClock can be either 'true' or 'false'. If set to
           'true' then a |/-\\| style animation will be displayed if
           the load operation takes more than 200 ms to complete.";
      }
      leaf instanceDescription {
        type boolean;
        default true;
        description
          "instanceDescription is either 'true' or 'false'. If 'true'
           then the CLI will look for description elems and add
           their values as info texts when displaying possible completions
           in the CLI. This makes it easier to identify the different
           instances.";
      }
      leaf addErrorPrefixSuffix {
        type boolean;
        default true;
        description
          "addErrorPrefixSuffix is either 'true' or 'false'. If 'true'
           then the CLI will add 'Error: ' or 'Aborted: ' and when operations
           fail  in the CLI. If set to 'false' then the prefix will not
           be added for errors generated by some callback.";
      }
      leaf compListCompact {
        type boolean;
        default false;
        description
          "compListCompact is either 'true' or 'false'. If 'true'
           then the CLI will display items with an associated info
           text one per line, and all the rest in compact format.";
      }
      leaf completionListLine {
        type boolean;
        default false;
        description
          "completionListLine is either 'true' or 'false'. If 'true'
           then the CLI will display completion lists one item per
           line. If set to 'false' one-line presentation will be
           used for itmes with info texts and compact for the rest.
           (if compListCompact above is set to 'true' there may be a
           mix of the to formats in the same listing)";
      }
      leaf infoOnMatch {
        type boolean;
        default true;
        description
          "infoOnMatch is either 'true' or 'false'. If 'true'
           then the CLI will add info texts when displaying
           possible match completions. If set to 'false' then
           the info text will not be shown.";
      }
      leaf externalActionErrorMsg {
        type string;
        description
          "The externalActionErrorMsg value is displayed whenever an
           external error occurs when executing an action in the CLI.";
      }
      leaf enableDisplayLevel {
        type enableDisplayLevelType;
        default pipe;
        description
          "enableDisplayLevel is either 'true', 'false' or 'pipe'. If 'false'
           then the 'displaylevel' option to the show command will not
           be available in the CLIs. If set to 'pipe' then a special
           pipe target called 'display-level' will be available.

           The displaylevel option can be used to limit how many levels
           will be displayed by the show command. If a display level of
           1 is specified then only the direct children of an
           element will be shown.  If a display level of 3 is specified
           then only elements at depth 3 below a given element
           will be displayed, etc.

           A user can also modify the default display level for a given
           CLI- session using the display-level setting in the CLI,
           similarly to the screen-width, or idle-timeout settings.";
      }
      leaf defaultDisplayLevel {
        type int64;
        default 99999999;
        description
          "If enableDisplayLevel is set to 'true' then this settings
           controls the default display level used if no explicit
           display level is specified. It is also used as the initial
           value of the (set) 'display-level' command in the CLI.";
      }
      leaf enableDisplayGroups {
        type boolean;
        default true;
        description
          "enableDisplayGroups is either 'true' or 'false'. If 'false'
           then the user will not be able to provide a set of display
           groups when issuing the show command.";
      }
      leaf unifiedHistory {
        type boolean;
        default false;
        description
          "If set to 'true' then the 'show history' command will
           display the unified command history, ie the command history
           from all modes. If set to 'false' then only the command
           history from the current mode will be shown.";
      }
      leaf modeInfoInAAA {
        type modeInfoInAAAType;
        default false;
        description
          "modeInfoInAAA is either 'true', 'false' or 'path', If 'true', then
           all commands will be prefixed with major and minor mode name
           when processed by the AAA-rules. This means that it is
           possible to differentiate between commands with the same
           name in different modes. Major mode is 'operational' or
           'configure' and minor mode is 'top' in J-style and the name
           of the submode in C- and I-mode. On the top-level in C- and
           I-mode it is also 'top'. If set to 'path' the major mode
           will be followed by the full command path to the submode.";
      }
      leaf cmdAAAForAutowizard {
        type boolean;
        default false;
        description
          "cmdAAAForAutowizard si either 'true' or 'false'. If set to
           'true' then the CLI will generate synthetic commands, and
           perform AAA command rule checks for, for all paths and
           values requested by the autowizard functionality.";
      }
      leaf quoteStyle {
        type quoteStyleType;
        default backslash;
        description
          "quoteStyle is either 'quote' or 'backslash'. If set to
           'quote' then the quote characters will be used on the CLI
           command line for quoting strings with troublesome
           characters. If set to 'backslash' then a backslash will be
           used. For example:

           Using quote:

           io(config)# description 'description with spaces'

           Using backslash:

           io(config)# description description\\ with\\ spaces";
      }
      leaf laxBarQuoting {
        type boolean;
        default false;
        description
          "laxBarQuoting is either 'true' or 'false'. If set to 'true'
           then | and ; are only quoted if they appear by them selves.
           A consequence of this is that the user must have whitespace
           on both sides of | and ; on the command line when these
           characters are used as pipe (|) or concatenator (;).";
      }
      leaf expandAliasOnCompletion {
        type boolean;
        default true;
        description
          "expandAliasOnCompletion is either true or false. If set to
           true then aliases will be expanded before invoking the
           completion code.";
      }
      leaf expandAliasEscape {
        type aliasQuoteType;
        default false;
        description
          "expandAliasEscape is either true or false. If set to
           true then expanding an alias can be prevented by putting
           a $ sign in front of the alias.";
      }
      leaf docWrap {
        type boolean;
        default true;
        description
          "docWrap is either 'true' or 'false'. If 'false' then certain
           documentation texts will not be enclosed in '<' and
           '>', if set to 'true' they will be.";
      }
      leaf infoOnTab {
        type boolean;
        default true;
        description
          "infoOnTab is either 'true' or 'false'. If 'false' then no
           info strings will be displayed in the tab completion list
           when the user enters TAB.";
      }
      leaf infoOnSpace {
        type boolean;
        default true;
        description
          "infoOnSpace is either 'true' or 'false'. If 'false' then no
           info strings will be displayed in the tab completion list
           when the user enters SPACE.";
      }
      leaf newLogout {
        type boolean;
        default true;
        description
          "newLogout is either 'true' or 'false'. If 'false' then the I
           and C modes will have a single 'logout' command for logging
           out a user and a specific session. If set to 'true' then
           there will be two different commands - 'logout user
           <name>' and 'logout session <id>'";
      }
      leaf newInsert {
        type boolean;
        default true;
        description
          "newInsert is either 'true' or 'false'. If 'false' then the old
           insert command will be used. If set to 'true' then the new
           insert command, capable of inserting ordered-by-user list
           elements, will be used.";
      }
      leaf messageFormat {
        type string;
        default "\\nMessage from $(sender) at $(time)...\\n$(message)\\nEOF\\n";
        description
          "messageFormat controls how messages between users and from
           the system should be presented to the user. The format
           string may contain the variables $(sender), $(time), $(message),
           $(date), $(time12), $(time12ampm), $(time12hm), $(host),
           $(hostname), and $(user).";
      }
      leaf messageWordWrap {
        type boolean;
        default false;
        description
          "messageWordWrap is either 'true' or 'false'. If set to 'true'
           then all system/user/prio messages in the CLI will be word-wrapped
           to the current terminal width.";
      }
      leaf messageQueueSize {
        type int64;
        default 10;
        description
          "Some messages are not displayed in the CLI when a command
           executed, but are delayed until the current command execution
           has finished. The size of the queue of pending messages is
           configured in messageQueueSize.";
      }
      leaf promptEnumLimit {
        type uint64 {
          range "0 .. max";
        }
        default 4;
        description
          "promptEnumLimit controls how many enumerations should be included
           in the prompt when prompting the user for a value where there are
           a number of alternatives. If the number of alternativies exceeds
           the above configured limit then the list will be truncated and
           the string '...' will be added.";
      }
      leaf caseInsensitive {
        type boolean;
        default false;
        description
          "caseInsensitive is either 'true' or 'false'. If 'false' then
           all CLI commands must have the correct case. If set to
           'true' then case is mostly ignored. Note that if set to
           'true' then all data model files and clispec-files must be
           written with this in mind. You cannot have two
           elems that conflict in case.";
      }
      leaf caseInsensitiveKeys {
        type boolean;
        default false;
        description
          "caseInsensitiveKeys is either 'true' or 'false'. If 'false' then
           all user defined instance names must have correct case. If set to
           'true' then case is mostly ignored. Note that if set to
           'true' then all data model files and clispec-files must be
           written with this in mind. You cannot have two
           elems that conflict in case.";
      }
      leaf ignoreLeadingWhitespace {
        type boolean;
        default false;
        description
          "ignoreLeadingWhitespace is either 'true' or 'false'. If
           'false' then the CLI will show completion help when the user
           enters TAB or SPACE as the first characters on a row. If set
           to 'true' then leading SPACE and TAB are ignored. The user
           can enter '?' to get a list of possible
           alternatives. Setting the value to 'true' makes it easier to
           paste scripts into the CLI.";
      }
      leaf indentTemplates {
        type boolean;
        default false;
        description
          "indentTemplates is either 'true' or 'false'. If set to 'true'
           then the text resulting from a show template will be indented
           to the same level as the surrounding auto-rendered show text.
           If set to 'false' then no automatic indentation will occur.
           The automatic variable '.indent' may be used in the templates
           to do manual indentation.";
      }
      leaf wrapInfo {
        type boolean;
        default true;
        description
          "wrapInfo is either 'true' or 'false'. If 'false' then the
           CLI will not automatically wrap the info field in 'Possible
           completion:' listings. If set to 'true' then the info text
           will be word-wrapped and indented.";
      }
      leaf wrapPrompt {
        type boolean;
        default false;
        description
          "wrapPrompt is either 'true' or 'false'. If 'false' then the
           CLI will not automatically word wrap the prompt when prompting
           the user for some input. If set to 'true' then the prompt
           will be word-wrapped according to the current terminal width.";
      }
      leaf sortShowElems {
        type boolean;
        default true;
        description
          "sortShowElems is either 'true' or 'false'. If 'false' then
           the show commands will display the elements in the order
           they appear in the data model. If set to 'true' then all
           non-dynamic elements will appear before the dynamic ones.
           This setting only applies to the C- and I-style CLIs.";
      }
      leaf showMatchBeforePossible {
        type boolean;
        default false;
        description
          "showMatchBeforePossible is either 'true' or 'false'. If set to
           'true' then the match completions will be displayed before
           the other possible completions, if set to 'false' then
           the match completions will be displayed after.";
      }
      leaf possibleCompletionsFormat {
        type string;
        default "Possible completions:";
        description
          "possibleCompletionsFormat is the string displayed before the
           displaying the actual completion possibilities.";
      }
      leaf matchCompletionsFormat {
        type string;
        default "Possible match completions:";
        description
          "matchCompletionsFormat is the string displayed before the
           displaying the actual match completion possibilities.";
      }
      leaf noMatchCompletionsFormat {
        type string;
        default "";
        description
          "noMatchCompletionsFormat is the string displayed when there
           are no matching completion possibilities. The string is empty
           by default.";
      }
      leaf showDescription {
        type boolean;
        default true;
        description
          "showDescription is either true or false. If set to false then
           the Description: xx text will not be displayed.";
      }
      leaf explicitSetCreate {
        type boolean;
        default false;
        description
          "explicitSetCreate is either 'true' or 'false'. If set to
           'true' then the 'set' command in J-style CLI cannot be used
           to create instances. Instead a new command called 'create'
           becomes available for creating instances. Note that this
           deviates from a typical Juniper style CLI where instance
           creation is performed by the 'set' command.";
      }
      list templateFilter {
        key name;
        description
          "User defined template filters must be listed here. They
           can be used in show templates in the same manner as the
           builtin ones. A template filter takes a string as input in
           'argv[1]' and returns a modified version of it by invoking
           'confd_action_reply_command'. It can also take extra
           arguments. For example '|a_filter:foo:42' implies
           'argv[2]='foo'' and 'argv[3]='42'.";
        leaf name {
          type string;
          description "Name of template filter.";
        }
        leaf callback {
          type string;
          description
            "Name of callback. The callback receives a string as first
             argument, optionally followed by the list of arguments
             given to the filter in the show template.";
        }
      }
      leaf escapeBackslash {
        type boolean;
        default false;
        description
          "escapeBackslash is either 'true' or 'false'. If 'true' then
           backslash is escaped in the CLI.";
      }
    }
    container webui {
      presence "";
      description
        "This section defines settings which decide how the embedded
         ConfD Web server should behave, with respect to TCP and SSL
         etc.";
      leaf enabled {
        type boolean;
        default false;
        description
          "enabled is either 'true' or 'false'. If 'true', the Web
           server is started.";
      }
      leaf serverName {
        type xs:token;
        default localhost;
        description "The hostname the Web server serves.";
      }
      leaf matchHostName {
        type boolean;
        default false;
        description
          "This setting specifies if the Web server only should serve
           URLs adhering to the serverName defined above. By default
           the serverName is 'localhost' and matchHostName is 'false',
           i.e. any server name can be given in the URL. If you want
           the server to only accept URLs adhering to the serverName,
           enable this setting.";
      }
      leaf cacheRefreshSecs {
        type uint64 {
          range "0 .. max";
        }
        default 0;
        description
          "The ConfD Web server uses a RAM cache for static content. An
           entry sits in the cache for a number of seconds before it is
           reread from disk (on access). The default is 0.";
      }
      leaf maxRefEntries {
        type uint64 {
          range "0 .. max";
        }
        default 100;
        description
          "Leafref and keyref entries are represented as drop-down
           menues in the automatically generated Web UI. By default
           no more than 100 entries are fetched. This element makes
           this number configurable.";
      }
      leaf docroot {
        type string;
        description
          "The location of the document root on disk. If this
           configurable is omited the docroot points to the next
           generation docroot in the ConfD distro instead.";
      }
      leaf webuiIndexUrl {
        type string;
        default "/index.html";
        description
          "Where to redirect after successful login, which by default
           is '/index.html'.";
      }
      leaf hatcheryUrl {
        type string;
        default "/webui";
        description
          "Url where the 'hatchery' webui is mapped if enabled.
           The default is '/webui'.";
      }
      leaf loginDir {
        type string;
        description
          "loginDir may be used if a custom login directory is to be
           used instead of the builtin ditto.";
      }
      leaf customDir {
        type string;
        description
          "customDir should be used if the Web UI is to be customized
           as described in the User Guide.";
      }
      container customHeaders {
        presence "";
        list header {
          key name;
          description
            "The customHeaders element contains any number of header
             elements, with a valid header-field as defined in RFC7230.

             The headers will be part of HTTP responses on '/login.html',
             '/index.html' and '/jsonrpc'.";
          leaf name {
            type string;
            description "Header name, e.g. Accept-Control-Allow-Origin";
          }
          leaf value {
            type string;
            mandatory true;
            description "Header value, e.g. http://www.cisco.com";
          }
        }
      }
      leaf X-Frame-Options {
        type X-Frame-OptionsType;
        default "DENY";
        description
          "By default the X-Frame-Options header is set to DENY for
           the /login.html and /index.html pages. With this header
           it can be set to SAMEORIGIN or ALLOW-FROM instead.";
      }
      container disableAuth {
        presence "";
        leaf-list dir {
          type string;
          description
            "The disableAuth element contains any number of dir
             elements. Each dir element points to a directory path
             in the docroot which should not be restricted by the AAA
             engine. If no dir elements are specifed the following
             directories and files will not be restricted by the AAA
             engine: '/login' and '/login.html'.";
        }
      }
      leaf allowSymlinks {
        type boolean;
        default true;
        description "Allow symlinks in the docroot directory.";
      }
      container transport {
        presence "";
        description
          "Settings deciding which transport services the Web server
           should listen to, e.g. TCP and SSL.";
        container tcp {
          presence "";
          description
            "Settings deciding how the Web server TCP transport service
             should behave.";
          leaf enabled {
            type boolean;
            default true;
            description
              "enabled is either 'true' or 'false'. If 'true', the Web
               server uses cleart text TCP as a transport service.";
          }
          leaf disableNonAuthRedirect {
            type boolean;
            default false;
            description
              "disableNonAuthRedirect is either 'true' or 'false'. If
               'true' non-authenticated HTTP requests (expect '/' and
               '/index.html') result in a 404 HTTP reply. If false
               all non-authenticated requests are redirected to
               '/login.html'.";
          }
          leaf redirect {
            type string;
            description
              "If given the user will be redirected to the specified
               URL. Two macros can be specified, i.e. @HOST@ and
               @PORT@. For example https://@HOST@:443 or
               https://192.12.4.3:@PORT@";
          }
          leaf ip {
            type inet:ip-address;
            default "0.0.0.0";
            description
              "The IP address which the Web server should listen
               to. 0.0.0.0 means that it listens to the port
               (/confdConfig/webui/transport/tcp/port) for all IPv4
               addresses on the machine.";
          }
          leaf port {
            type inet:port-number;
            default 8008;
            description
              "port is a valid port number to be used in combination
               with the address in /confdConfig/webui/transport/tcp/ip.";
          }
          leaf-list extraIpPorts {
            type xs:token;
            description
              "extraIpPorts is a leaf-list of ip:port
               pairs which the Web server also listens to for TCP connections.";
          }
          leaf dscp {
            type dscpType;
            description
              "Support for setting the Differentiated Services Code Point
               (6 bits) for traffic originating from the Web server for
               TCP connections.";
          }
        }
        container ssl {
          presence "";
          description
            "Settings deciding how the Web server SSL (Secure Sockets
             Layer) transport service should behave.

             SSL is widely deployed on the Internet and virtually all
             bank transactions as well as all on-line shopping today is
             done with SSL encryption. There are many good sources on
             describing SSL in detail,
             e.g. http://www.tldp.org/HOWTO/SSL-Certificates-HOWTO/
             which describes how to manage certificates and keys.";
          leaf enabled {
            type boolean;
            default false;
            description
              "enabled is either 'true' or 'false'. If 'true', the Web
               server uses SSL as a transport service.";
          }
          leaf disableNonAuthRedirect {
            type boolean;
            default false;
            description
              "disableNonAuthRedirect is either 'true' or 'false'. If
               'true' non-authenticated HTTP requests (expect '/' and
               '/index.html') result in a 404 HTTP reply. If false
               all non-authenticated requests are redirected to
               '/login.html'.";
          }
          leaf redirect {
            type string;
            description
              "If given the user will be redirected to the specified
               URL. Two macros can be specified, i.e. @HOST@ and
               @PORT@. For example http://@HOST@:80 or
               http://192.12.4.3:@PORT@";
          }
          leaf ip {
            type inet:ip-address;
            default "0.0.0.0";
            description
              "The IP address which the Web server should listen to for
               incoming ssl connections. 0.0.0.0 means that it listens
               to the port (/confdConfig/webui/transport/ssl/port) for
               all IPv4 addresses on the machine.";
          }
          leaf port {
            type inet:port-number;
            default 8888;
            description
              "port is a valid port number to be used in combination
               with /confdConfig/webui/transport/ssl/ip.";
          }
          leaf-list extraIpPorts {
            type xs:token;
            description
              "extraIpPorts is a leaf-list of ip:port
               pairs which the Web server also listens to for SSL connections.";
          }
          leaf dscp {
            type dscpType;
            description
              "Support for setting the Differentiated Services Code Point
               (6 bits) for traffic originating from the Web server for
               SSL connections.";
          }
          leaf keyFile {
            type string;
            description
              "Specifies which file that contains the private key for
               the certificate. Read more about certificates in
               /confdConfig/webui/transport/ssl/certFile. If this
               configurable is omitted the keyFile points to a
               built-in self signed certificate/key in the ConfD
               distro instead. Note: Only use this certificate/key
               for test purposes.";
          }
          leaf certFile {
            type string;
            description
              "Specifies which file that contains the server
               certificate. The certificate is either a self-signed
               test certificate or a genuin and validated certificate
               bought from a CA (Certificate Authority). If this
               configurable is omitted the keyFile points to a
               built-in self signed certificate/key in the ConfD
               distro instead. Note: Only use this certificate/key
               for test purposes.

               The ConfD distro comes with a server certificate
               which can be used for testing purposes
               ($CONFD_DIST/src/confd/webui/cert/host.{cert,key}). This
               server certificate has been generated using a local CA
               certificate:

               $ openssl
               OpenSSL> genrsa -out ca.key 4096
               OpenSSL> req -new -x509 -days 3650 -key ca.key -out ca.cert
               OpenSSL> genrsa -out host.key 4096
               OpenSSL> req -new -key host.key -out host.csr
               OpenSSL> x509 -req -days 365 -in host.csr -CA ca.cert
                 -CAkey ca.key -set_serial 01 -out host.cert";
          }
          leaf caCertFile {
            type string;
            description
              "Specifies which file that contains the trusted
               certificates to use during client authentication and
               to use when attempting to build the server certificate
               chain. The list is also used in the list of acceptable
               CA certificates passed to the client when a
               certificate is requested.

               The ConfD distro comes with a CA certificate
               which can be used for testing purposes
               ($CONFD_DIST/src/confd/webui/ca_cert/ca.cert).
               This CA certificate has been generated as shown above.";
          }
          leaf verify {
            type verifyType;
            default 1;
            description
              "Specifies the level of verification the server does on
               client certificates. 1 means nothing, 2 means the
               server will ask the client for a certificate but not
               fail if the client does not supply a client
               certificate, 3 means that the server requires the
               client to supply a client certificate.

               If caCertFile has been set to the ca.cert file
               generated above you can verify that it works correctly
               using, for example:

               $ openssl s_client -connect 127.0.0.1:8888
                     -cert client.cert -key client.key

               For this to work client.cert must have been generated using
               the ca.cert from above:

               $ openssl
               OpenSSL> genrsa -out client.key 4096
               OpenSSL> req -new -key client.key -out client.csr
               OpenSSL> x509 -req -days 3650 -in client.csr -CA ca.cert
                 -CAkey ca.key
                 -set_serial 01 -out client.cert";
          }
          leaf depth {
            type uint64 {
              range "0 .. max";
            }
            default 1;
            description
              "Specifies the depth of certificate chains the server
               is prepared to follow when verifying client
               certificates.";
          }
          leaf ciphers {
            type string;
            default DEFAULT;
            description
              "Specifies the cipher suites to be used by the server as a
               colon-separated list from the set
               ECDHE-ECDSA-AES256-GCM-SHA384, ECDHE-RSA-AES256-GCM-SHA384,
               ECDHE-ECDSA-AES256-SHA384, ECDHE-RSA-AES256-SHA384,
               ECDH-ECDSA-AES256-GCM-SHA384, ECDH-RSA-AES256-GCM-SHA384,
               ECDH-ECDSA-AES256-SHA384, ECDH-RSA-AES256-SHA384,
               DHE-RSA-AES256-GCM-SHA384, DHE-DSS-AES256-GCM-SHA384,
               DHE-RSA-AES256-SHA256, DHE-DSS-AES256-SHA256,
               AES256-GCM-SHA384, AES256-SHA256,
               ECDHE-ECDSA-AES128-GCM-SHA256, ECDHE-RSA-AES128-GCM-SHA256,
               ECDHE-ECDSA-AES128-SHA256, ECDHE-RSA-AES128-SHA256,
               ECDH-ECDSA-AES128-GCM-SHA256, ECDH-RSA-AES128-GCM-SHA256,
               ECDH-ECDSA-AES128-SHA256, ECDH-RSA-AES128-SHA256,
               DHE-RSA-AES128-GCM-SHA256, DHE-DSS-AES128-GCM-SHA256,
               DHE-RSA-AES128-SHA256, DHE-DSS-AES128-SHA256,
               AES128-GCM-SHA256, AES128-SHA256, ECDHE-ECDSA-AES256-SHA,
               ECDHE-RSA-AES256-SHA, DHE-RSA-AES256-SHA, DHE-DSS-AES256-SHA,
               ECDH-ECDSA-AES256-SHA, ECDH-RSA-AES256-SHA, AES256-SHA,
               ECDHE-ECDSA-DES-CBC3-SHA, ECDHE-RSA-DES-CBC3-SHA,
               EDH-RSA-DES-CBC3-SHA, EDH-DSS-DES-CBC3-SHA,
               ECDH-ECDSA-DES-CBC3-SHA, ECDH-RSA-DES-CBC3-SHA, DES-CBC3-SHA,
               ECDHE-ECDSA-AES128-SHA, ECDHE-RSA-AES128-SHA,
               DHE-RSA-AES128-SHA, DHE-DSS-AES128-SHA, ECDH-ECDSA-AES128-SHA,
               ECDH-RSA-AES128-SHA, AES128-SHA, EDH-RSA-DES-CBC-SHA, and
               DES-CBC-SHA, or the word 'DEFAULT' (use all supported
               cipher suites in that list). See the OpenSSL manual page
               ciphers(1) for the definition of the cipher suites.
               NOTE: The general cipher list syntax described in
               ciphers(1) is not supported.";
          }
          leaf protocols {
            type string;
            default DEFAULT;
            description
              "Specifies the SSL/TLS protocol versions to be used by the
               server as a whitespace-separated list from the set
               sslv3 tlsv1 tlsv1.1 tlsv1.2, or the word 'DEFAULT' (use all
               supported protocol versions except sslv3).";
          }
        }
      }
      container cgi {
        presence "";
        description "CGI-script support";
        leaf enabled {
          type boolean;
          default false;
          description
            "enabled is either 'true' or 'false'. If 'true',
             CGI-script support is enabled.";
        }
        leaf dir {
          type string;
          default cgi-bin;
          description
            "
             The directory path to the location of the CGI-scripts.";
        }
        leaf requestFilter {
          type string;
          description
            "Specifies that characters not specified in the given
             regexp should be filtered out silently.";
        }
        leaf maxRequestLength {
          type uint16;
          description
            "Specifies the maximum amount of characters in a
             request. All characters exceedig this limit are silenty
             ignored.";
        }
        container php {
          presence "";
          description "PHP support";
          leaf enabled {
            type boolean;
            default false;
            description
              "enabled is either 'true' or 'false'. If 'true',
               PHP support is enabled.";
          }
        }
      }
      leaf idleTimeout {
        type xs:duration;
        default PT30M;
        description
          "
           Maximum idle time before terminating a Web UI session.
           PT0M means no timeout. Default is PT30M, ie 30 minutes.";
      }
      leaf absoluteTimeout {
        type xs:duration;
        default PT60M;
        description
          "Maximum absolute time before terminating a Web UI session.
           PT0M means no timeout. Default is PT60M, ie 60 minutes.";
      }
      leaf rateLimiting {
        type uint64 {
          range "0 .. max";
        }
        default 1000000;
        description
          "Maximum number of allowed JSON-RPC requests every hour.
           0 means infinity. Default is 1 million.";
      }
      container namedCommands {
        presence "";
        description
          "Named commands are used to define a well defined set
           of executables which can be run on the target device from
           the browser using a call to Maapi.runCmd().";
        list exec {
          key name;
          description
            "The 'exec' directive specifies how a named command is
             mapped to an executable or a shell script. It contains
             (in order) one 'name' directive, one 'osCommand'
             directive, zero or one 'args' directives and zero or one
             'options' directives.

             An example:

             <namedCommands>
              <exec>
                <name>cli</name>
                <osCommand>confd_cli</osCommand>
                <args>-u$(user) --proto http</args>
              </exec>
             <namedCommands>";
          leaf name {
            type xs:token;
            mandatory true;
            description
              "The command alias name to be used in Maapi.runCmd() calls.";
          }
          leaf osCommand {
            type string;
            mandatory true;
            description
              "The 'osCommand' directive specifies the path to the
               executable or shell script to be called. If the command
               is in the $PATH (as specified when we start the
               ConfD daemon) the path may just be the name of the
               command.

               The command is invoked as if it had been executed by
               exec(3), i.e. not in a shell environment such as
               '/bin/sh -c ...";
          }
          leaf args {
            type string;
            description
              "The 'args' directive specifies the arguments to use when
               executing the command specified by the 'osCommand'
               directive. args is a space-separated list of
               argument strings.";
          }
          container options {
            presence "";
            description
              "The 'options' directive specifies how the command is be
               executed. It contains (in any order) zero or one 'uid'
               directives and zero or one 'wd' directives.";
            leaf uid {
              type idType;
              description
                "The 'uid' directive specifies which user id to use when
                 executing the command. Possible values are:

                 confd (default): The command is run as the same user id
                 as the ConfD daemon.

                 user: The command is run as the same user id as the user
                 logged in to the CLI, i.e. we have to make sure that
                 this user id exists as an actual user id on the device.

                 root: The command is run as root.

                 <uid> (the numerical user <uid>): The
                 command is run as the user id <uid>.

                 NOTE: If uid is set to either 'user', 'root' or
                 <uid> the ConfD daemon must have been started as
                 root (or setuid), or the cmdptywrapper must have setuid
                 root permissions.";
            }
            leaf wd {
              type string;
              description
                "The 'wd' directive specifies which working directory to
                 use when executing the command. If not given, the
                 command is executed from the location of the CLI.";
            }
            leaf globalNoDuplicate {
              type string;
            }
          }
        }
      }
      leaf audit {
        type boolean;
        default false;
        description
          "audit is either 'true' or 'false'. If 'true', then JSON-RPC/CGI
           requests are logged to the audit log.";
      }
    }
    container rest {
      presence "";
      description
        "This section defines settings for the experimental REST api.";
      leaf enabled {
        type boolean;
        default false;
        description
          "enabled is either 'true' or 'false'. If 'true', the
           experimental REST api is enabled on the Web server used by
           the Web UI.  Note that the Web UI must be enabled as well.";
      }
      leaf showHidden {
        type boolean;
        default false;
        description
          "Hidden nodes are not shown by default in REST.  Such nodes can be
           unhidden to the REST client by including the query parameter
           'unhide', which is a comma separated list of

           <hide-group-name>[;<passwd>]


           If showHidden is set to 'true', hidden nodes are always shown
           in the REST API.";
      }
      container customHeaders {
        presence "";
        list header {
          key name;
          description
            "The customHeaders element contains any number of header
             elements, with a valid header-field as defined in RFC7230.";
          leaf name {
            type string;
            description "Header name, e.g. Accept-Control-Allow-Origin";
          }
          leaf value {
            type string;
            mandatory true;
            description "Header value, e.g. http://www.cisco.com";
          }
        }
      }
    }
    container restconf {
      presence "";
      description
        "This section defines settings for the RESTCONF api.";
      leaf enabled {
        type boolean;
        default false;
        description
          "enabled is either 'true' or 'false'. If 'true', the RESTCONF api is
           enabled on the Web server used by the Web UI.  Note that the Web UI
           must be enabled as well.";
      }
      leaf rootResource {
        type string;
        default "restconf";
        description
          "The RESTCONF root resource path.";
      }
    }
    container capi {
      presence "";
      description "C-API parameters.";
      leaf newSessionTimeout {
        type xs:duration;
        default PT30S;
        description
          "
           Timeout for a daemon to respond to a control socket request,
           see confd_lib_dp(3). If the daemon fails to respond within the
           given time, it will be disconnected.";
      }
      leaf queryTimeout {
        type xs:duration;
        default PT120S;
        description
          "Timeout for a daemon to respond to a worker socket query,
           see confd_lib_dp(3). If the daemon fails to respond within the
           given time, it will be disconnected.";
      }
      leaf connectTimeout {
        type xs:duration;
        default PT60S;
        description
          "Timeout for daemon to send initial message after connecting
           the socket to the confd server. If the daemon fails to
           initiate the connection within the given time, it will be
           disconnected.";
      }
      leaf objectCacheTimeout {
        type xs:duration;
        default PT2S;
        description
          "Timeout for the cache used by the get_object() and
           get_next_object() callback requests, see confd_lib_dp(3).
           ConfD caches the result of these calls and serves get_elem
           requests from northbound agents from the cache.
           NOTE: Setting this timeout too low will effectively cause
           the callbacks to be non-functional - e.g. get_object() may
           be invoked for each get_elem request from a northbound agent.";
      }
      leaf eventReplyTimeout {
        type xs:duration;
        default PT120S;
        description
          "Timeout for the reply from an event notification subscriber
           for a notification that requires a reply, see
           confd_lib_events(3). If the subscriber fails to reply within
           the given time, the notification socket will be closed.";
      }
    }
    container proxyForwarding {
      presence "";
      description
        "This section defines settings which affect the behavior of
         Proxy Forwarding.";
      leaf enabled {
        type boolean;
        default false;
        description
          "enabled is either 'true' or 'false'. If 'true', proxy
           forwarding is enabled.";
      }
      leaf autoLogin {
        type boolean;
        default false;
        description
          "autoLogin is either 'true' or 'false'. If 'true', ConfD will
           try to login to the target system with the current
           session\\'s credentials, if it has access to them.  In order
           for ConfD to get access to the session credentials, the
           builtin SSH daemon must be used.";
      }
      list proxy {
        key target;
        description "Parameters for a single proxy.";
        leaf target {
          type xs:token;
          description
            "The name of the proxy target. It is used as a unique
             identifier of the proxy target.  This is the target name
             that users give when they want to connect to the target.

             The name is included in the proxy events (see
             confd_lib_events(3)) generated by ConfD.";
        }
        leaf address {
          type inet:host;
          mandatory true;
          description "The IP address of the proxy target system.";
        }
        container netconf {
          presence "";
          description
            "If present, the target is available for NETCONF proxy
             forwarding.";
          choice transport1 {
            container ssh {
              description
                "If present, the proxy connections between ConfD and
                 the proxy NETCONF target will be over SSH.";
              leaf port {
                type inet:port-number;
                default 2022;
                description
                  "The port where the proxy target listens for NETCONF
                   SSH connections.";
              }
            }
            container tcp {
              description
                "If present, the proxy connections between ConfD and
                 the proxy NETCONF target will be over TCP.";
              leaf port {
                type inet:port-number;
                default 2023;
                description
                  "The port where the proxy target listens for NETCONF
                   TCP connections.";
              }
            }
          }
        }
        container cli {
          presence "";
          description
            "If present, the target is available for CLI proxy forwarding.";
          choice transport {
            container ssh {
              description
                "If present, the proxy connections between ConfD and
                 the proxy CLI target will be over SSH.";
              leaf port {
                type inet:port-number;
                default 22;
                description
                  "The port where the proxy target listens for CLI SSH
                   connections.";
              }
            }
          }
        }
      }
    }
    container snmpAgent {
      presence "";
      description
        "This section defines settings which affect the behavior of the
         SNMP agent.";
      leaf enabled {
        type boolean;
        default false;
        description
          "enabled is either 'true' or 'false'. If 'true', the SNMP
           agent is enabled.";
      }
      leaf ip {
        type inet:ip-address;
        default "0.0.0.0";
        description
          "ip is an IP address which the ConfD SNMP agent should listen
           to. 0.0.0.0 means that it listens to the port
           (/confdConfig/snmpAgent/port) for all IPv4
           addresses on the machine.";
      }
      leaf port {
        type inet:port-number;
        default 161;
        description
          "port is a valid port number to be used in combination with
           /confdConfig/snmpAgent/ip.";
      }
      leaf-list extraIpPorts {
        type xs:token;
        description
          "extraIpPorts is a leaf-list of ip:port
           pairs which the SNMP agent also listens to.";
      }
      leaf dscp {
        type dscpType;
        description
          "Support for setting the Differentiated Services Code Point
           (6 bits) for traffic originating from the SNMP agent.";
      }
      container mibs {
        presence "";
        description "A list of MIBs that should be loaded into the SNMP agent.";
        leaf-list file {
          type string;
          description
            "file is the location of a MIB file that should be loaded
             into the SNMP agent. For example:
             <file>./TAIL-F-TEST-MIB.bin</file>.  The MIB
             file must be in binary format (.bin) produced with the
             confdc compiler.  For loading of a built-in MIB no path
             must be given.

             Example: <file>SNMP-USER-BASED-SM-MIB.bin</file>.

             See the ConfD User Guide for more information about
             loading MIBs into the SNMP agent.";
        }
        leaf fromLoadPath {
          type boolean;
          default false;
          description
            "If true, any '.bin' file found in the
             /confdConfig/loadPath is loaded at startup.  Bult-in
             MIBs must still be listed explicitly using the 'file' element.";
        }
      }
      leaf temporaryStorageTime {
        type uint32;
        default 300;
        description
          "The time, in seconds, that the agent keeps temporary table
           entries before deleting them.  A table entry is temporary
           if its RowStatus column is 'notReady' or 'notInService'.";
      }
      container snmpVersions {
        presence "";
        description
          "The list of SNMP versions that the SNMP agent will
           understand.";
        leaf v1 {
          type boolean;
          default true;
          description
            "Setting the value to true will enable SNMP v1 in the SNMP
             agent.";
        }
        leaf v2c {
          type boolean;
          default true;
          description
            "Setting the value to true will enable SNMP v2c in the SNMP
             agent.";
        }
        leaf v3 {
          type boolean;
          default true;
          description
            "Setting the value to true will enable SNMP v3 in the SNMP
             agent.";
        }
      }
      container snmpEngine {
        presence "";
        description
          "Properties from the SNMP-FRAMEWORK-MIB (RFC3411) for the
           SNMP agent.";
        leaf snmpEngineID {
          type tailf:hex-list;
          mandatory true;
          description
            "The name of the SNMP engine. snmpEngineID is defined in
             the SNMP-FRAMEWORK-MIB (RFC3411).";
        }
        leaf snmpEngineMaxMessageSize {
          type uint64 {
            range "0 .. max";
          }
          default 50000;
          description
            "The maximum size of SNMP messages that the agent can send
             or receive.  The snmpEngineMaxMessageSize is defined in
             the SNMP-FRAMEWORK-MIB (RFC3411).";
        }
      }
      leaf sessionIgnorePort {
        type boolean;
        default false;
        description
          "If true, the SNMP Agent will consider requests originating
           from one and the same IP Address, and using the same security
           name, as related, regardless of source port.
           Per default, the SNMP Agent will consider requests originating
           from one and the same IP Address and port, and using the same
           security name, as related.
           Related requests are handled in the same user session. This is
           absolutely necessary for achieving good performance when processing
           consecutive get-next requests, as during SNMP walks.";
      }
      leaf authenticationFailureNotifyName {
        type string;
        default "";
        description
          "When the SNMP agent sends the standard
           authenticationFailure notification, it is delivered to the
           management targets defined for the snmpNotifyName in the
           snmpNotifyTable in SNMP-NOTIFICATION-MIB (RFC3413).  If
           authenticationFailureNotifyName is the empty string
           (default), the notification is delivered to all management
           targets.";
      }
      container candidate {
        presence "";
        description
          "Directives for how to manage locks and changes to the candidate
           when processing SNMP set requests in systems where
           /confdConfig/datastores/running/access is
           writable-through-candidate.
           When running with this datastore setup, the SNMP Agent must
           lock the candidate before making changes to it and committing
           those to the running configuration.";
        leaf maxLockWait {
          type xs:duration;
          default PT0S;
          description
            "If the candidate is locked by another user session, the SNMP
             Agent will send a resourceUnavailable response unless the
             candidate becomes available for locking within this time period.
             The default value is PT0S, which means the error response will
             be sent immediately.";
        }
        leaf pendingChangesAction {
          type pendingChangesActionType;
          default continue;
          description
            "If there are pending changes in the candidate when the SNMP
             Agent attempts to lock it, these will be discarded (continue) or
             the lock will not be taken and the SNMP request will fail with
             resourceUnavailable (fail). The default value is continue.";
        }
      }
      leaf dropWhenInUse {
        type boolean;
        default false;
        description
          "Whenever a set request cannot be completed, due to competing
           actions (typically CDB clients, or other transactions) preventing
           the SNMP Agent from taking the required locks on configuration
           stores and data providers affected by the request, the SNMP Agent
           will respond to the set request with an 'in use' error.
           If dropWhenInUse is true, the SNMP Agent will silently drop the
           request instead.";
      }
      leaf-list contexts {
        type SNMPContextNameType;
        description
          "contexts is a leaf-list of context names
           which this SNMP Agent, i.e. one or more external data
           providers recognize in addition to the empty context, ''.";
      }
      container system {
        presence "";
        description
          "The properties from the SNMPv2-MIB (RFC3418) for the SNMP agent.";
        leaf sysDescr {
          type string;
          description
            "A textual description of the entity.  This value should
             include the full name and version identification of the
             system's hardware type, software operating-system, and
             networking software.  The sysDescr is defined in the
             SNMPv2-MIB (RFC3418).";
        }
        leaf sysObjectID {
          type yang:object-identifier;
          description
            "The vendor's authoritative identification of the network
             management subsystem contained in the entity.  The
             sysObjectID is defined in the SNMPv2-MIB (RFC3418).";
        }
        leaf sysServices {
          type uint64 {
            range "0 .. max";
          }
          default 72;
          description
            "A value which indicates the set of services that this
             entity may potentially offer.  The sysServices is defined
             in the SNMPv2-MIB (RFC3418).";
        }
        container sysORTable {
          presence "";
          description
            "Entries that will populate the sysORTable from SNMPv2-MIB.";
          list sysOREntry {
            key sysORIndex;
            leaf sysORIndex {
              type uint64 {
                range "0 .. max";
              }
              description "The index for this row in the table.";
            }
            leaf sysORID {
              type yang:object-identifier;
              mandatory true;
              description "The OID of the AGENT-CAPABILITIES invocation.";
            }
            leaf sysORDescr {
              type string;
              mandatory true;
              description
                "A textual description of capabilities defined in sysORID.";
            }
          }
        }
      }
    }
    container netconf {
      presence "";
      description
        "This section defines settings which decide how the NETCONF
         server should behave, with respect to NETCONF and SSH.";
      leaf enabled {
        type boolean;
        default true;
        description
          "enabled is either 'true' or 'false'. If 'true', the NETCONF
           server is started.";
      }
      container versions {
        presence "";
        description
          "The list of NETCONF versions that the NETCONF server will
           understand.";
        leaf "v1.0" {
          type boolean;
          default true;
          description
            "Setting the value to true will enable NETCONF version
             1.0, as defined in RFC 4741.";
        }
        leaf "v1.1" {
          type boolean;
          default true;
          description
            "Setting the value to true will enable NETCONF version
             1.1, as defined in draft-ietf-netconf-4741bis-10.txt.";
        }
      }
      container transport {
        presence "";
        description
          "Settings deciding which transport services the NETCONF server
           should listen to, e.g. TCP and SSH.";
        container ssh {
          presence "";
          description
            "Settings deciding how the NETCONF SSH transport service
             should behave.";
          leaf enabled {
            type boolean;
            default true;
            description
              "enabled is either 'true' or 'false'. If 'true', the
               NETCONF server uses SSH as a transport service.";
          }
          leaf ip {
            type inet:ip-address;
            default "0.0.0.0";
            description
              "ip is an IP address which the ConfD NETCONF server should
               listen to. 0.0.0.0 means that it listens to the port
               (/confdConfig/netconf/transport/ssh/port) for all IPv4
               addresses on the machine.";
          }
          leaf port {
            type inet:port-number;
            default 2022;
            description
              "port is a valid port number to be used in combination
               with /confdConfig/netconf/transport/ssh/ip.  Note that
               the standard port for NETCONF over SSH is 830.";
          }
          leaf-list extraIpPorts {
            type xs:token;
            description
              "extraIpPorts is a leaf-list of ip:port
               pairs which the NETCONF server also listens to for
               SSH connections.";
          }
          leaf dscp {
            type dscpType;
            description
              "Support for setting the Differentiated Services Code Point
               (6 bits) for traffic originating from the NETCONF server for
               SSH connections.";
          }
        }
        container tcp {
          presence "";
          description
            "NETCONF over TCP is not standardized, but it can be useful
             during development in order to use e.g. netcat for
             scripting. It is also useful if we want to use our own
             proprietary transport. In that case we setup the NETCONF
             server to listen to localhost and then proxy it from our
             transport service module.";
          leaf enabled {
            type boolean;
            default false;
            description
              "enabled is either 'true' or 'false'. If 'true', the
               NETCONF server uses clear text TCP as a transport
               service.";
          }
          leaf ip {
            type inet:ip-address;
            default "0.0.0.0";
            description
              "ip is an IP address which the ConfD NETCONF server should
               listen to. 0.0.0.0 means that it listens to the port
               (/confdConfig/netconf/transport/tcp/port) for all IPv4
               addresses on the machine.";
          }
          leaf port {
            type inet:port-number;
            default 2023;
            description
              "port is a valid port number to be used in combination
               with /confdConfig/netconf/transport/tcp/ip.";
          }
          leaf-list extraIpPorts {
            type xs:token;
            description
              "extraIpPorts is a leaf-list of ip:port
               pairs which the NETCONF server also listens to for
               TCP connections.";
          }
          leaf dscp {
            type dscpType;
            description
              "Support for setting the Differentiated Services Code Point
               (6 bits) for traffic originating from the NETCONF server for
               TCP connections.";
          }
        }
      }
      leaf extendedSessions {
        type boolean;
        default false;
        description
          "If extendedSessions are enabled, all ConfD sessions can be
           terminated using <kill-session>, i.e. not only can
           other NETCONF session be terminated, but also CLI sessions,
           Webui sessions etc.  If such a session holds a lock, it's
           session id will be returned in the <lock-denied>,
           instead of '0'.

           Strictly speaking, this extension is not covered by the
           NETCONF specification; therefore it's false by default.";
      }
      leaf sendDefaults {
        type boolean;
        default false;
        tailf:info "DEPRECATED - use defaultHandlingMode instead";
        description
          "DEPRECATED - use /confdConfig/defaultHandlingMode instead
           to control this behavior consistently for all northbound
           interfaces.

           If sendDefaults is true, default values will be included in
           the replies to <get>, <get-config>, and
           <copy-config>.  If sendDefaults is false, default
           values will not be included by default.

           If /confdConfig/netconf/capabilities/with-defaults is
           enabled, this behavior can be controlled by the NETCONF
           client.";
      }
      leaf idleTimeout {
        type xs:duration;
        default PT0S;
        description
          "Maximum idle time before terminating a NETCONF session.
           If the session is waiting for notifications, or has a
           pending confirmed commit, the idle timeout is not used.
           The default value is 0, which means no timeout.

           Modification of this value will only affect connections that
           are established after the modification has been done.";
      }
      leaf writeTimeout {
        type xs:duration;
        default PT0S;
        description
          "Maximum time for a write operation towards a client to complete.
           If the time is exceeded, the NETCONF session is terminated.
           The default value is 0, which means no timeout.

           Modification of this value will only affect connections that
           are established after the modification has been done.";
      }
      leaf rpcErrors {
        type rpcErrorType;
        default close;
        description
          "If rpcErrors is 'inline', and an error occurs during the
           processing of a <get> or <get-config> request when ConfD
           tries to fetch some data from a data provider, ConfD will
           generate an rpc-error element in the faulty element, and
           continue to process the next element.

           If an error occurs and rpcErrors is 'close', the NETCONF
           transport is closed by ConfD.";
      }
      leaf maxBatchProcesses {
        type limitType;
        default unbounded;
        description
          "Controls how many concurrent NETCONF batch processes there
           can be at any time.  A batch process can be started by the
           server if a new NETCONF operation is implemented as a batch
           operation.  See the NETCONF chapter in the ConfD User's
           Guide for details.";
      }
      container capabilities {
        presence "";
        description "Decide which NETCONF capabilities to enable here.";
        container startup {
          presence "";
          leaf enabled {
            type boolean;
            default false;
            description
              "enabled is either 'true' or 'false'. If 'true', the
               startup NETCONF capability is enabled. Enable only if
               /confdConfig/datastores/startup is enabled.";
          }
        }
        container candidate {
          presence "";
          leaf enabled {
            type boolean;
            default true;
            description
              "enabled is either 'true' or 'false'. If 'true', the
               candidate NETCONF capability is enabled. Enable only if
               /confdConfig/datastores/candidate is enabled.";
          }
        }
        container confirmed-commit {
          presence "";
          leaf enabled {
            type boolean;
            default true;
            description
              "enabled is either 'true' or 'false'. If 'true', the
               confirmed-commit NETCONF capability is enabled.";
          }
        }
        container writable-running {
          presence "";
          leaf enabled {
            type boolean;
            default true;
            description
              "enabled is either 'true' or 'false'. If 'true', the
               writable-running NETCONF capability is enabled. Enable
               only if /confdConfig/datastores/running/access is
               read-write.";
          }
        }
        container rollback-on-error {
          presence "";
          leaf enabled {
            type boolean;
            default true;
            description
              "enabled is either 'true' or 'false'. If 'true', the
               rollback-on-error NETCONF capability is enabled.";
          }
        }
        container validate {
          presence "";
          leaf enabled {
            type boolean;
            default true;
            description
              "enabled is either 'true' or 'false'. If enabled 'true',
               the validate NETCONF capability is enabled.";
          }
          leaf test-only {
            type boolean;
            default false;
            description
              "DEPRECATED - this feature is available in NETCONF 1.1.

               If test-only 'true', the NETCONF server allows
               'test-only' as a valid value for the
               '<test-option>' parameter in
               '<edit-config>'.";
          }
        }
        container url {
          presence "";
          description "Turn on the URL capability options we want to support.";
          leaf enabled {
            type boolean;
            default false;
            description
              "enabled is either 'true' or 'false'. If 'true', the url
               NETCONF capability is enabled.";
          }
          container file {
            presence "";
            description "Decide how the url file support should behave.";
            leaf enabled {
              type boolean;
              default true;
              description
                "enabled is either 'true' or 'false'. If 'true', the
                 url file scheme is enabled.";
            }
            leaf rootDir {
              type string;
              mandatory true;
              description
                "rootDir is a directory path on disk where ConfD will
                 store the result from an NETCONF operation using the
                 url capability.  This parameter must be set if the
                 file url scheme is enabled.";
            }
          }
          container ftp {
            presence "";
            description "Decide how the url ftp scheme should behave.";
            leaf enabled {
              type boolean;
              default true;
              description
                "enabled is either 'true' or 'false'. If 'true', the
                 url ftp scheme is enabled.";
            }
          }
          container sftp {
            presence "";
            description "Decide how the url sftp scheme should behave.";
            leaf enabled {
              type boolean;
              default true;
              description
                "enabled is either 'true' or 'false'. If 'true', the
                 url sftp scheme is enabled.";
            }
          }
        }
        container xpath {
          presence "";
          leaf enabled {
            type boolean;
            default true;
            description
              "enabled is either 'true' or 'false'. If 'true', the
               xpath capability is enabled.";
          }
        }
        container notification {
          presence "";
          leaf enabled {
            type boolean;
            default false;
            description
              "enabled is either 'true' or 'false'. If 'true', the
               notification capability, defined in RFC 5277, is enabled.";
          }
          container interleave {
            presence "";
            leaf enabled {
              type boolean;
              default false;
              description
                "enabled is either 'true' or 'false'. If 'true', the
                 interleave capability, defined in RFC 5277, is
                 enabled.  With this capability enabled, the NETCONF
                 server will process RPCs while sending notifications.";
            }
          }
        }
        container actions {
          presence "";
          leaf enabled {
            type boolean;
            default false;
            description
              "enabled is either 'true' or 'false'. If 'true', the
               'http://tail-f.com/ns/netconf/actions/1.0' capability is
               enabled.";
          }
        }
        container transactions {
          presence "";
          leaf enabled {
            type boolean;
            default false;
            description
              "enabled is either 'true' or 'false'. If 'true', the
               'http://tail-f.com/ns/netconf/transactions/1.0'
               capability is enabled.";
          }
        }
        container with-defaults {
          presence "";
          leaf enabled {
            type boolean;
            default false;
            description
              "DEPRECATED - use ietf-with-defaults instead.

               enabled is either 'true' or 'false'. If 'true', the
               'http://tail-f.com/ns/netconf/with-defaults/1.0'
               capability is enabled.";
          }
        }
        container ietf-with-defaults {
          presence "";
          leaf enabled {
            type boolean;
            default true;
            description
              "enabled is either 'true' or 'false'. If 'true', the
                with-defaults capability, defined in
                draft-ietf-netconf-with-defaults-14, is enabled.

                The NETCONF server will advertise its 'basic-mode' and
                'also-supported' modes depending on the parameter
                /confdConfig/defaultHandlingMode.";
          }
        }
        container partial-lock {
          presence "";
          leaf enabled {
            type boolean;
            default false;
            description
              "enabled is either 'true' or 'false'. If 'true', the
               partial-lock capability as defined in RFC 5717 is enabled.";
          }
        }
        container forward {
          presence "";
          leaf enabled {
            type boolean;
            default false;
            description
              "enabled is either 'true' or 'false'. If 'true', the
               'http://tail-f.com/ns/netconf/forward/1.0' capability is
               enabled.";
          }
        }
        container tailf-commit {
          presence "";
          leaf enabled {
            type boolean;
            default false;
            description
              "DEPRECATED - this feature is available in NETCONF 1.1.

               enabled is either 'true' or 'false'. If 'true', the
               'http://tail-f.com/ns/netconf/commit/1.0' capability is
               enabled.";
          }
        }
        container query {
          presence "";
          leaf enabled {
            type boolean;
            default false;
            description
              "enabled is either 'true' or 'false'. If 'true', the
               'http://tail-f.com/ns/netconf/query' capability is
               enabled.";
          }
        }
        container extensions {
          presence "";
          leaf enabled {
            type boolean;
            default true;
            description
              "enabled is either 'true' or 'false'. If 'true', the
               'http://tail-f.com/ns/netconf/extensions' capability is
               enabled.";
          }
        }
        container inactive {
          presence "";
          leaf enabled {
            type boolean;
            default false;
            description
              "enabled is either 'true' or 'false'. If 'true', the
               'http://tail-f.com/ns/netconf/inactive/1.0' capability is
               enabled.";
          }
        }
        leaf-list capability {
          type inet:uri;
          description
            "capability is a parameter can be given multiple times. It
             specifies a URI string which the NETCONF server will report
             as a capability in the hello message sent to the client.";
        }
      }
    }

    // NCS-specific, not documented here
    container southboundSourceAddress {
      presence "";
      leaf ipv4 {
        type inet:ipv4-address;
      }
      leaf ipv6 {
        type inet:ipv6-address;
      }
    }
  }
}
